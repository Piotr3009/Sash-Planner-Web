;;; ARKA BARY R8 - V1
;;; Based on: arka_CNC - piotr.dxf, units: millimetres.
;;; AutoCAD for Windows with Visual LISP/ActiveX.
;;; Creates 2D vectors only. No G-code, cutter compensation or machining depths.
;;; Original objects are never edited or deleted.
;;; Output layer names retain source names with the prefix ARKA_.
;;; SECTION: one open polyline; quarter circle R8 + vertical straight 6.
;;; MITRE: open two-segment corner vectors following the offset contour.
;;; IMPORTANT: closed PANE is the inner rail for a Vectric outward moulding sweep.
;;; FRONT_HINGES_3MM is a legacy SOURCE NAME for the outer profile limit,
;;; not a drilling operation and not the inner moulding drive rail.

(vl-load-com)
(if (not (boundp '*arka-pane*)) (setq *arka-pane* 2.0))
(if (not (boundp '*arka-radius*)) (setq *arka-radius* 8.0))
(if (not (boundp '*arka-straight*)) (setq *arka-straight* 6.0))
(if (not (boundp '*arka-leg*)) (setq *arka-leg* 15.0))
(setq *arka-created* nil)

(defun ar:fail (msg)
  (princ (strcat "\nARKA: " msg))
  (exit)
)
(defun ar:track (en)
  (if en (setq *arka-created* (cons en *arka-created*)))
  en
)
(defun ar:delete (en)
  (if (and en (entget en)) (entdel en))
)
(defun ar:run (fn / result doc en oldgap)
  (setq *arka-created* nil)
  (setq doc (vla-get-ActiveDocument (vlax-get-acad-object)))
  (vla-StartUndoMark doc)
  (setq oldgap (getvar "OFFSETGAPTYPE"))
  (setvar "OFFSETGAPTYPE" 0)
  (setq result (vl-catch-all-apply fn nil))
  (setvar "OFFSETGAPTYPE" oldgap)
  (if (vl-catch-all-error-p result)
    (progn
      (foreach en *arka-created* (ar:delete en))
      (princ (strcat "\nPrzerwano. Usunieto tylko nowo utworzone obiekty. "
                     (vl-catch-all-error-message result)))
    )
  )
  (vla-EndUndoMark doc)
  (setq *arka-created* nil)
  (princ)
)
(defun ar:units (/ ans)
  (if (/= (getvar "TILEMODE") 1)
    (ar:fail "Przejdz do zakladki MODEL przed uruchomieniem."))
  (cond
    ((= (getvar "INSUNITS") 4) T)
    ((= (getvar "INSUNITS") 0)
      (initget "Tak Nie")
      (setq ans (getkword "\nRysunek bez jednostek. Czy 1 jednostka to 1 mm? [Tak/Nie] <Nie>: "))
      (if (= ans "Tak")
        (progn (setvar "INSUNITS" 4) T)
        (ar:fail "Nie potwierdzono milimetrow. Rysunek nie zostal przeskalowany.")))
    (T (ar:fail "Wymagane mm (INSUNITS=4). Zweryfikuj skale rysunku, nie tylko etykiete jednostek."))
  )
)
(defun ar:layer (name col / rec)
  (setq rec (tblsearch "LAYER" name))
  (if rec
    (if (or (/= 0 (logand (cdr (assoc 70 rec)) 5))
            (< (cdr (assoc 62 rec)) 0))
      (ar:fail (strcat "Warstwa " name " jest zablokowana, zamrozona lub wylaczona.")))
    (if (not (entmake
          (list '(0 . "LAYER") '(100 . "AcDbSymbolTableRecord")
                '(100 . "AcDbLayerTableRecord") (cons 2 name) '(70 . 0)
                (cons 62 col) '(6 . "Continuous")
                (cons 290 (if (= name "ARKA_INFO_NO_CUT") 0 1)))))
      (ar:fail (strcat "Nie mozna utworzyc warstwy " name))))
  name
)
(defun ar:layers (/ item)
  (foreach item '(("ARKA_OUTLINE" 7) ("ARKA_PANE" 3) ("ARKA_PANE_ZEWN_REF" 3)
                 ("ARKA_FRONT_HINGES_3MM" 50) ("ARKA_MITRE" 1)
                 ("ARKA_SECTION" 5) ("ARKA_INFO_NO_CUT" 8))
    (ar:layer (car item) (cadr item)))
)
(defun ar:xy (p) (list (car p) (cadr p)))
(defun ar:add (p q) (list (+ (car p) (car q)) (+ (cadr p) (cadr q))))
(defun ar:sub (p q) (list (- (car p) (car q)) (- (cadr p) (cadr q))))
(defun ar:scale (p fac) (list (* (car p) fac) (* (cadr p) fac)))
(defun ar:len (p q)
  (sqrt (+ (expt (- (car q) (car p)) 2) (expt (- (cadr q) (cadr p)) 2))))
(defun ar:tan (ang) (/ (sin ang) (cos ang)))
(defun ar:shift (verts delta)
  (mapcar '(lambda (v) (list (+ (car v) (car delta))
                            (+ (cadr v) (cadr delta)) (caddr v))) verts))
(defun ar:vertices (en / data out cur pair)
  (setq data (entget en) out nil cur nil)
  (foreach pair data
    (cond
      ((= (car pair) 10)
        (if cur (setq out (cons cur out)))
        (setq cur (list (cadr pair) (caddr pair) 0.0)))
      ((and (= (car pair) 42) cur)
        (setq cur (list (car cur) (cadr cur) (cdr pair))))))
  (if cur (setq out (cons cur out)))
  (reverse out)
)
(defun ar:poly (verts closed layer / data v)
  (setq data (list '(0 . "LWPOLYLINE") '(100 . "AcDbEntity")
                   '(67 . 0) '(410 . "Model") (cons 8 layer)
                   '(100 . "AcDbPolyline") (cons 90 (length verts))
                   (cons 70 (if closed 1 0)) '(38 . 0.0) '(43 . 0.0)))
  (foreach v verts
    (setq data (append data (list (cons 10 (ar:xy v)) (cons 42 (caddr v))))))
  (setq data (append data '((210 0.0 0.0 1.0))))
  (if (entmake data) (ar:track (entlast))
    (ar:fail "Nie udalo sie utworzyc polilinii."))
)
(defun ar:text (pt h txt / data)
  (setq data (list '(0 . "TEXT") '(100 . "AcDbEntity") '(67 . 0)
                   '(410 . "Model") '(8 . "ARKA_INFO_NO_CUT")
                   '(100 . "AcDbText") (cons 10 (list (car pt) (cadr pt) 0.0))
                   (cons 40 h) (cons 1 txt) '(7 . "Standard") '(50 . 0.0)))
  (if (entmake data) (ar:track (entlast)))
)
(defun ar:valid (en / d verts n idx v nxt)
  (setq d (entget en))
  (if (/= (cdr (assoc 0 d)) "LWPOLYLINE")
    (ar:fail "Wejscie musi byc LWPOLYLINE z liniami/lukami, nie SPLINE ani osia bara."))
  (if (= 0 (logand 1 (cdr (assoc 70 d))))
    (ar:fail "Otwarty obrys. Najpierw sprawdz szczeline i zamknij obwod pola (PEDIT)."))
  (if (or (and (assoc 38 d) (> (abs (cdr (assoc 38 d))) 1e-8))
          (and (assoc 210 d) (not (equal (cdr (assoc 210 d)) '(0.0 0.0 1.0) 1e-8))))
    (ar:fail "Wymagane obrysy w plaszczyznie WCS XY, Z=0, normalna +Z."))
  (if (or (and (assoc 43 d) (> (abs (cdr (assoc 43 d))) 1e-8))
          (vl-some '(lambda (x) (and (member (car x) '(40 41))
                                      (> (abs (cdr x)) 1e-8))) d))
    (ar:fail "Obrys ma szerokosc polilinii. Uzyj polilinii o szerokosci 0."))
  (setq verts (ar:vertices en) n (length verts) idx 0)
  (if (< n 2) (ar:fail "Za malo wierzcholkow."))
  (repeat n
    (setq v (nth idx verts) nxt (nth (rem (1+ idx) n) verts))
    (if (< (ar:len v nxt) 1e-8)
      (ar:fail "Zerowy odcinek lub powtorzony wierzcholek. Sprawdz obrys."))
    (setq idx (1+ idx)))
  verts
)
;;; Analytic circular-arc geometry. No faceting is used in generated DXF curves.
;;; Segment record: (p q bulge sweep length centre radius).
(defun ar:seg (v nxt / p q bul chord ang centre rad fac dx dy leng)
  (setq p (ar:xy v) q (ar:xy nxt) bul (caddr v) chord (ar:len p q))
  (if (< chord 1e-9) (ar:fail "Zerowa dlugosc segmentu."))
  (if (< (abs bul) 1e-12)
    (list p q 0.0 0.0 chord nil 0.0)
    (progn
      (setq ang (* 4.0 (atan bul))
            rad (/ (* chord (+ 1.0 (* bul bul))) (* 4.0 (abs bul)))
            fac (/ (- 1.0 (* bul bul)) (* 4.0 bul))
            dx (- (car q) (car p)) dy (- (cadr q) (cadr p))
            centre (list (- (/ (+ (car p) (car q)) 2.0) (* dy fac))
                         (+ (/ (+ (cadr p) (cadr q)) 2.0) (* dx fac)))
            leng (* rad (abs ang)))
      (list p q bul ang leng centre rad))))
(defun ar:at (seg frac / p q centre vec ang)
  (setq p (nth 0 seg) q (nth 1 seg))
  (if (< (abs (nth 2 seg)) 1e-12)
    (ar:add p (ar:scale (ar:sub q p) frac))
    (progn
      (setq centre (nth 5 seg) vec (ar:sub p centre) ang (* frac (nth 3 seg)))
      (ar:add centre
        (list (- (* (car vec) (cos ang)) (* (cadr vec) (sin ang)))
              (+ (* (car vec) (sin ang)) (* (cadr vec) (cos ang))))))))
(defun ar:tangent (seg atend / vec ang)
  (setq vec (ar:sub (nth 1 seg) (nth 0 seg))
        ang (atan (cadr vec) (car vec)))
  (+ ang (* (if atend 0.5 -0.5) (nth 3 seg))))
(defun ar:corner-data (verts leg / n idx prv cur pin pout lt rt f1 f2 dlt out short)
  (setq n (length verts) idx 0 out nil short 0)
  (repeat n
    (setq prv (ar:seg (nth (rem (+ idx n -1) n) verts) (nth idx verts))
          cur (ar:seg (nth idx verts) (nth (rem (1+ idx) n) verts))
          dlt (- (ar:tangent cur nil) (ar:tangent prv T))
          dlt (abs (atan (sin dlt) (cos dlt))))
    ;; Skip smooth arc joins / collinear subdivision vertices.
    (if (> dlt (* pi (/ 0.5 180.0)))
      (progn
        ;; Keep opposite corner vectors separate on short segments.
        (setq lt (min leg (* 0.45 (nth 4 prv)))
              rt (min leg (* 0.45 (nth 4 cur))))
        (if (or (< lt (- leg 1e-7)) (< rt (- leg 1e-7))) (setq short (1+ short)))
        (setq f1 (/ lt (nth 4 prv)) f2 (/ rt (nth 4 cur))
              pin (ar:at prv (- 1.0 f1)) pout (ar:at cur f2))
        (setq out
          (cons
            (list (list (car pin) (cadr pin) (ar:tan (/ (* (nth 3 prv) f1) 4.0)))
                  (list (car (nth idx verts)) (cadr (nth idx verts))
                        (ar:tan (/ (* (nth 3 cur) f2) 4.0)))
                  (list (car pout) (cadr pout) 0.0)) out))))
    (setq idx (1+ idx)))
  (list (reverse out) short)
)
(defun ar:mitres (en / result vv)
  (setq result (ar:corner-data (ar:vertices en) *arka-leg*))
  (foreach vv (car result) (ar:poly vv nil "ARKA_MITRE"))
  (if (> (cadr result) 0)
    (princ (strcat "\nUwaga: " (itoa (cadr result))
      " narozniki maja skrocone ramiona (max. 45% dlugosci sasiedniego odcinka).")))
  (length (car result))
)
;;; Native OFFSET is attempted in both signs. Area determines inward/outward.
;;; Disconnected, multiple or open results are rejected; no silent largest-piece selection.
(defun ar:offset (en dist grow layer / obj area sign result objects cand chosen ar idx ob)
  (setq obj (vlax-ename->vla-object en) area (abs (vla-get-Area obj)) chosen nil)
  (if (< dist 1e-9)
    (ar:poly (ar:vertices en) T layer)
    (progn
      (foreach sign '(1.0 -1.0)
        (if (not chosen)
          (progn
            (setq result (vl-catch-all-apply 'vla-Offset (list obj (* sign dist))))
            (if (not (vl-catch-all-error-p result))
              (progn
                (setq objects (vlax-safearray->list (vlax-variant-value result)))
                (foreach ob objects (ar:track (vlax-vla-object->ename ob)))
                (if (= (length objects) 1)
                  (progn
                    (setq cand (car objects))
                    (if (and (= (vla-get-ObjectName cand) "AcDbPolyline")
                             (= (vla-get-Closed cand) :vlax-true))
                      (progn
                        (setq ar (abs (vla-get-Area cand)))
                        (if (if grow (> ar (+ area 1e-7)) (< ar (- area 1e-7)))
                          (setq chosen cand))))))
                (foreach ob objects
                  (if (not (eq ob chosen)) (ar:delete (vlax-vla-object->ename ob)))))))))
      (if (not chosen)
        (ar:fail (strcat "Nie mozna wykonac pojedynczego zamknietego OFFSET "
                         (rtos dist 2 3) ". Sprawdz promienie, petle i szerokosci.")))
      (vla-put-Layer chosen layer)
      (vlax-vla-object->ename chosen)))
)
(defun ar:bounds (entities / lo hi p q obj bb)
  (foreach en entities
    (setq obj (vlax-ename->vla-object en))
    (vla-GetBoundingBox obj 'p 'q)
    (setq p (vlax-safearray->list p) q (vlax-safearray->list q))
    (if (not lo) (setq lo (ar:xy p) hi (ar:xy q))
      (setq lo (list (min (car lo) (car p)) (min (cadr lo) (cadr p)))
            hi (list (max (car hi) (car q)) (max (cadr hi) (cadr q))))))
  (list lo hi)
)
(defun ar:profile (pt / r h vv)
  (setq r *arka-radius* h *arka-straight*
        vv (list (list 0.0 0.0 (- (ar:tan (/ pi 8.0)))) (list r r 0.0)))
  (if (> h 1e-9) (setq vv (append vv (list (list r (+ r h) 0.0)))))
  (ar:poly (ar:shift vv pt) nil "ARKA_SECTION")
)
(defun ar:profile-note (pt / r h)
  (setq r *arka-radius* h *arka-straight*)
  (ar:text (ar:add pt '(0.0 30.0)) 3.0 "SECTION - JEDNA OTWARTA POLILINIA")
  (ar:text (ar:add pt '(0.0 24.0)) 2.5
    (strcat "Luk R" (rtos r 2 2) " + pion " (rtos h 2 2)
            "; W=" (rtos r 2 2) ", H=" (rtos (+ r h) 2 2) " mm"))
  (ar:text (ar:add pt '(0.0 -9.0)) 2.5 "Start: niski koniec przy PANE. Wektor nie jest programem CNC.")
  (ar:text (ar:add pt '(0.0 -15.0)) 2.5 "PANE -> granica FRONT_HINGES_3MM: szerokosc R.")
)
(defun ar:crossings (entities / list1 other en res arr cnt)
  (setq list1 entities cnt 0)
  (while list1
    (setq en (car list1))
    (foreach other (cdr list1)
      (setq res (vl-catch-all-apply 'vla-IntersectWith
                  (list (vlax-ename->vla-object en) (vlax-ename->vla-object other) 0)))
      (if (not (vl-catch-all-error-p res))
        (progn
          (setq arr (vl-catch-all-apply 'vlax-safearray->list
                       (list (vlax-variant-value res))))
          (if (and (not (vl-catch-all-error-p arr)) arr) (setq cnt (1+ cnt))))))
    (setq list1 (cdr list1)))
  cnt
)
(defun ar:process (outer fields delta / copies rails en pane rail mitrecount all bb pp cnt vv)
  (setq copies nil rails nil mitrecount 0)
  (if outer
    (progn
      (setq en (ar:poly (ar:shift outer delta) T "ARKA_OUTLINE"))
      (setq copies (cons en copies))
      (ar:offset en *arka-pane* nil "ARKA_PANE_ZEWN_REF")))
  (foreach vv fields
    (setq en (ar:poly (ar:shift vv delta) T "ARKA_OUTLINE"))
    (setq copies (cons en copies))
    (setq pane (ar:offset en *arka-pane* T "ARKA_PANE"))
    (setq rail (ar:offset en (+ *arka-pane* *arka-radius*) T "ARKA_FRONT_HINGES_3MM"))
    (setq rails (cons rail rails))
    (setq mitrecount (+ mitrecount (ar:mitres rail))))
  (setq bb (ar:bounds copies)
        pp (list (+ 60.0 (car (cadr bb))) (+ 45.0 (cadr (car bb)))))
  (ar:profile pp) (ar:profile-note pp)
  (ar:text (list (car (car bb)) (+ 25.0 (cadr (cadr bb)))) 4.0
           "ARKA - OBWODY POL + OFFSET + MITRE + SECTION")
  (ar:text (list (car (car bb)) (+ 16.0 (cadr (cadr bb)))) 3.0
           (strcat "PANE=" (rtos *arka-pane* 2 2) "; PROFIL=" (rtos *arka-radius* 2 2)
                   "; LIMIT=" (rtos (+ *arka-pane* *arka-radius*) 2 2)
                   "; MITRE=" (rtos *arka-leg* 2 2) " mm"))
  (if (<= (length rails) 150)
    (progn
      (setq cnt (ar:crossings rails))
      (if (> cnt 0)
        (princ (strcat "\nUWAGA: " (itoa cnt) " par obwodow profilu przecina sie. Nie kieruj do CNC.")))))
  (princ (strcat "\nGotowe: " (itoa (length fields)) " pol, "
                 (itoa mitrecount) " naroznikow, 1 przekroj. Warstwy ARKA_*."))
  (princ "\nTo geometria CAD. Sprawdz kierunek profilu, grubosc, kolizje i symulacje CAM.")
)
(defun ar:pick-outer (/ pick)
  (setq pick (entsel "\nWskaz OUTLINE ZEWN. calego okna [Enter = bez obrysu zewn.]: "))
  (if pick (progn (ar:valid (car pick)) (car pick)))
)
(defun ar:main (/ outer sel en idx fields sources bbox p delta expected)
  (ar:units) (ar:layers)
  (setq outer (ar:pick-outer))
  (princ "\nZaznacz tylko bazowe zamkniete OBWODY POL miedzy barami, nie ich osie.")
  (princ "\nNie zaznaczaj jednoczesnie istniejacych PANE, profili ani naroznikow.")
  (setq sel (ssget '((0 . "LWPOLYLINE"))))
  (if (not sel) (ar:fail "Nie wybrano pol."))
  (setq idx 0 fields nil sources nil)
  (repeat (sslength sel)
    (setq en (ssname sel idx))
    (if (not (eq en outer))
      (progn
        (setq fields (cons (ar:valid en) fields))
        (setq sources (cons en sources))))
    (setq idx (1+ idx)))
  (if (not fields) (ar:fail "Wybrano tylko obrys zewnetrzny."))
  (if outer (setq sources (cons outer sources)))
  (setq bbox (ar:bounds sources)
        expected (list (+ (car (cadr bbox)) 100.0) (cadr (car bbox)) 0.0))
  (setq p (getpoint (strcat "\nLewy dolny rog KOPII [Enter = obok, +100 mm]: ")))
  (if p (setq p (trans p 1 0)) (setq p expected))
  (setq delta (ar:sub p (car bbox)))
  (ar:process (if outer (ar:vertices outer)) (reverse fields) delta)
)
(defun c:ARKABARY () (ar:run 'ar:main))
(defun ar:profile-cmd (/ p)
  (ar:units) (ar:layers)
  (setq p (getpoint "\nPunkt wstawienia dolnego lewego konca przekroju: "))
  (if (not p) (ar:fail "Nie wskazano punktu."))
  (setq p (trans p 1 0))
  (ar:profile (ar:xy p)) (ar:profile-note (ar:xy p))
  (princ "\nSECTION: 1 otwarta polilinia. Nie zamykaj jej poleceniem JOIN/CLOSE.")
)
(defun c:ARKAPROFIL () (ar:run 'ar:profile-cmd))
(defun ar:get-real (label val allowzero / result)
  (initget (if allowzero 4 6))
  (setq result (getreal (strcat "\n" label " <" (rtos val 2 3) ">: ")))
  (if result result val)
)
(defun c:ARKAUSTAW (/ p r h leg)
  (setq p (ar:get-real "OFFSET PANE od OUTLINE [mm]" *arka-pane* T)
        r (ar:get-real "Promien cwiercluku i szerokosc profilu R [mm]" *arka-radius* nil)
        h (ar:get-real "Pionowa prosta przekroju [mm]" *arka-straight* T)
        leg (ar:get-real "Dlugosc kazdego ramienia MITRE po krzywej [mm]" *arka-leg* nil))
  (setq *arka-pane* p *arka-radius* r *arka-straight* h *arka-leg* leg)
  (princ (strcat "\nZapisano. Zewnetrzny limit profilu = " (rtos (+ p r) 2 3)
                 "; wysokosc przekroju = " (rtos (+ r h) 2 3) " mm."))
  (princ "\nZmiana dotyczy kolejnych wynikow, nie modyfikuje juz narysowanych obiektow.")
  (princ)
)
(defun c:ARKARESET ()
  (setq *arka-pane* 2.0 *arka-radius* 8.0 *arka-straight* 6.0 *arka-leg* 15.0)
  (princ "\nARKA: ustawienia z przykladu: PANE 2, R8, pion 6, MITRE 15 mm.") (princ))

;;; Embedded demonstration input is appended below by the build script.
;;; START EMBEDDED DEMO
(setq ar:demo-outer '((607.000000000000 599.999166666089 0.417588105771) (0.000000000000 0.000000000000 0.000000000000) (601.000000000000 0.000000000000 0.000000000000) (607.000000000000 0.000000000000 0.000000000000)))
(setq ar:demo-fields '(((589.000000000000 581.896038824807 0.189105846842) (196.315539594441 419.240809591663 0.000000000000) (317.261393666373 298.294955519731 -0.185035351434) (589.000000000000 410.852771683484 0.000000000000))
((180.759190408337 403.684460405559 0.185992220930) (18.278417110041 18.000000000001 0.000000000000) (189.394349770976 18.000000000001 -0.180632309217) (301.705044480268 282.738606333627 0.000000000000))
((589.000000000000 388.844441904472 0.184252429810) (332.823632895702 282.732716290403 0.000000000000) (458.781530335538 156.774818850565 -0.171936199756) (589.000000000000 210.713075057055 0.000000000000))
((317.267283709597 267.176367104299 0.179601516981) (211.416675602259 18.000000000001 0.000000000000) (389.769174477194 18.000000000001 -0.163388565032) (443.225181149435 141.218469664462 0.000000000000))
((589.000000000000 188.997354478840 0.368577824255) (411.859095356698 18.000000000001 0.000000000000) (589.000000000000 18.000000000001 0.000000000000))))

(defun ar:demo (/ p)
  (ar:units) (ar:layers)
  (setq p (getpoint "\nLewy dolny rog przykladu [Enter = 0,0]: "))
  (if p (setq p (trans p 1 0)) (setq p '(0.0 0.0 0.0)))
  (ar:process ar:demo-outer ar:demo-fields (ar:xy p))
  (princ "\nDemo uzywa OUTLINE z pliku, ale oblicza stale offsety od nowa.")
  (princ "\nTo nie jest bezstratna kopia wszystkich pomocniczych linii z pliku zrodlowego.")
)
(defun c:ARKADEMO () (ar:run 'ar:demo))
(defun c:ARKA ()
  (princ "\nARKADEMO  - przyklad z zalaczonego DXF, z aktualnymi ustawieniami")
  (princ "\nARKABARY  - twoje zamkniete obwody pol + opcjonalny obrys zewnetrzny")
  (princ "\nARKAPROFIL - sam przekroj, 1 otwarta polilinia")
  (princ "\nARKAUSTAW - odstep PANE, promien R, pion, ramiona MITRE")
  (princ "\nARKARESET - ustawienia z przykladu: 2 / 8 / 6 / 15 mm")
  (princ "\nWejscie: LWPOLYLINE, proste i luki kolowe, zamkniete, WCS XY Z=0.")
  (princ "\nNie interpretuje automatycznie sieci otwartych osi barow ani SPLINE.")
  (princ))
(princ "\nWczytano ARKA BARY V1. Polecenia: ARKA / ARKADEMO / ARKABARY / ARKAPROFIL.")
(princ)
