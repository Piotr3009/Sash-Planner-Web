;;; ARKA tracery — generated by Production Core (ARCHED-WINDOWS-v3 Block 0.4)
;;; window CIR - pattern sunburst - units mm - layers ARKA_*
;;; The DXF of the same name carries the same entities; ARKA_INFO_NO_CUT is never machined.
(defun ar:layer (name col)
  (if (not (tblsearch "LAYER" name))
    (command "_.-LAYER" "_M" name "_C" (itoa col) name "")
    (command "_.-LAYER" "_S" name ""))
)
(defun ar:poly (layer closed verts / data v)
  (setq data (list (quote (0 . "LWPOLYLINE")) (quote (100 . "AcDbEntity")) (cons 8 layer)
                   (quote (100 . "AcDbPolyline")) (cons 90 (length verts)) (cons 70 (if closed 1 0))))
  (foreach v verts
    (setq data (append data (list (cons 10 (list (+ (car *ar-ip*) (car v)) (+ (cadr *ar-ip*) (cadr v)))) (cons 42 (caddr v))))))
  (entmake data)
)
(defun ar:point (layer x y)
  (entmake (list (quote (0 . "POINT")) (cons 8 layer) (cons 10 (list (+ (car *ar-ip*) x) (+ (cadr *ar-ip*) y) 0.0))))
)
(defun ar:text (layer x y h str)
  (entmake (list (quote (0 . "TEXT")) (cons 8 layer) (cons 10 (list (+ (car *ar-ip*) x) (+ (cadr *ar-ip*) y) 0.0)) (cons 40 h) (cons 1 str)))
)
(defun c:ARKA ( / ip)
  (setq ip (getpoint "\nInsertion point <0,0>: "))
  (setq *ar-ip* (if ip (list (car ip) (cadr ip)) (list 0.0 0.0)))
  (ar:layer "ARKA_OUTLINE" 7)
  (ar:layer "ARKA_PANE" 3)
  (ar:layer "ARKA_FRONT_HINGES_3MM" 50)
  (ar:layer "ARKA_MITRE" 1)
  (ar:layer "ARKA_SECTION" 5)
  (ar:layer "ARKA_PANE_ZEWN_REF" 3)
  (ar:layer "ARKA_CENTRE" 6)
  (ar:layer "ARKA_INFO_NO_CUT" 8)
  (ar:poly "ARKA_OUTLINE" T (list (598.5 305.5 1.0) (12.5 305.5 1.0)))
  (ar:poly "ARKA_PANE_ZEWN_REF" T (list (596.5 305.5 1.0) (14.5 305.5 1.0)))
  (ar:poly "ARKA_OUTLINE" T (list (580.279912 316.5 0.246619) (452.416235 537.966384 0.0) (373.016041 400.441214 -0.217871) (421.479524 316.5 0.0)))
  (ar:poly "ARKA_PANE" T (list (582.353752 314.5 0.250608) (451.721105 540.762382 0.0) (370.367099 399.853111 -0.226201) (419.64574 314.5 0.0)))
  (ar:poly "ARKA_FRONT_HINGES_3MM" T (list (590.498246 306.5 0.26607) (448.865148 551.815721 0.0) (359.613678 397.22764 -0.262923) (411.995305 306.5 0.0)))
  (ar:poly "ARKA_OUTLINE" T (list (433.363677 548.966384 0.246619) (177.636323 548.966384 0.0) (257.036517 411.441214 -0.217871) (353.963483 411.441214 0.0)))
  (ar:poly "ARKA_PANE" T (list (436.132647 549.762382 0.250608) (174.867353 549.762382 0.0) (256.221359 408.853111 -0.226201) (354.778641 408.853111 0.0)))
  (ar:poly "ARKA_FRONT_HINGES_3MM" T (list (447.133097 552.815721 0.26607) (163.866903 552.815721 0.0) (253.118373 398.22764 -0.262923) (357.881627 398.22764 0.0)))
  (ar:poly "ARKA_OUTLINE" T (list (158.583765 537.966384 0.246619) (30.720088 316.5 0.0) (189.520476 316.5 -0.217871) (237.983959 400.441214 0.0)))
  (ar:poly "ARKA_PANE" T (list (159.278895 540.762382 0.250608) (28.646248 314.5 0.0) (191.35426 314.5 -0.226201) (240.632901 399.853111 0.0)))
  (ar:poly "ARKA_FRONT_HINGES_3MM" T (list (162.134852 551.815721 0.26607) (20.501754 306.5 0.0) (199.004695 306.5 -0.262923) (251.386322 397.22764 0.0)))
  (ar:poly "ARKA_OUTLINE" T (list (30.720088 294.5 0.246619) (158.583765 73.033616 0.0) (237.983959 210.558786 -0.217871) (189.520476 294.5 0.0)))
  (ar:poly "ARKA_PANE" T (list (28.646248 296.5 0.250608) (159.278895 70.237618 0.0) (240.632901 211.146889 -0.226201) (191.35426 296.5 0.0)))
  (ar:poly "ARKA_FRONT_HINGES_3MM" T (list (20.501754 304.5 0.26607) (162.134852 59.184279 0.0) (251.386322 213.77236 -0.262923) (199.004695 304.5 0.0)))
  (ar:poly "ARKA_OUTLINE" T (list (177.636323 62.033616 0.246619) (433.363677 62.033616 0.0) (353.963483 199.558786 -0.217871) (257.036517 199.558786 0.0)))
  (ar:poly "ARKA_PANE" T (list (174.867353 61.237618 0.250608) (436.132647 61.237618 0.0) (354.778641 202.146889 -0.226201) (256.221359 202.146889 0.0)))
  (ar:poly "ARKA_FRONT_HINGES_3MM" T (list (163.866903 58.184279 0.26607) (447.133097 58.184279 0.0) (357.881627 212.77236 -0.262923) (253.118373 212.77236 0.0)))
  (ar:poly "ARKA_OUTLINE" T (list (452.416235 73.033616 0.246619) (580.279912 294.5 0.0) (421.479524 294.5 -0.217871) (373.016041 210.558786 0.0)))
  (ar:poly "ARKA_PANE" T (list (451.721105 70.237618 0.250608) (582.353752 296.5 0.0) (419.64574 296.5 -0.226201) (370.367099 211.146889 0.0)))
  (ar:poly "ARKA_FRONT_HINGES_3MM" T (list (448.865148 59.184279 0.26607) (590.498246 304.5 0.0) (411.995305 304.5 -0.262923) (359.613678 213.77236 0.0)))
  (ar:poly "ARKA_OUTLINE" T (list (400.0 305.5 1.0) (211.0 305.5 1.0)))
  (ar:poly "ARKA_PANE" T (list (402.0 305.5 1.0) (209.0 305.5 1.0)))
  (ar:poly "ARKA_FRONT_HINGES_3MM" T (list (410.0 305.5 1.0) (201.0 305.5 1.0)))
  (ar:poly "ARKA_MITRE" nil (list (575.498246 306.5 0.0) (590.498246 306.5 0.013159) (590.050995 321.491599 0.0)))
  (ar:poly "ARKA_MITRE" nil (list (461.624628 543.932591 0.013159) (448.865148 551.815721 0.0) (441.365148 538.82534 0.0)))
  (ar:poly "ARKA_MITRE" nil (list (367.113678 410.218021 0.0) (359.613678 397.22764 -0.035226) (371.954543 388.722856 0.0)))
  (ar:poly "ARKA_MITRE" nil (list (410.800379 321.439894 -0.035226) (411.995305 306.5 0.0) (426.995305 306.5 0.0)))
  (ar:poly "ARKA_MITRE" nil (list (439.633097 539.82534 0.0) (447.133097 552.815721 0.013159) (433.926367 559.92419 0.0)))
  (ar:poly "ARKA_MITRE" nil (list (177.073633 559.92419 0.013159) (163.866903 552.815721 0.0) (171.366903 539.82534 0.0)))
  (ar:poly "ARKA_MITRE" nil (list (245.618373 411.218021 0.0) (253.118373 398.22764 -0.035226) (266.654164 404.66275 0.0)))
  (ar:poly "ARKA_MITRE" nil (list (344.345836 404.66275 -0.035226) (357.881627 398.22764 0.0) (365.381627 411.218021 0.0)))
  (ar:poly "ARKA_MITRE" nil (list (169.634852 538.82534 0.0) (162.134852 551.815721 0.013159) (149.375372 543.932591 0.0)))
  (ar:poly "ARKA_MITRE" nil (list (20.949005 321.491599 0.013159) (20.501754 306.5 0.0) (35.501754 306.5 0.0)))
  (ar:poly "ARKA_MITRE" nil (list (184.004695 306.5 0.0) (199.004695 306.5 -0.035226) (200.199621 321.439894 0.0)))
  (ar:poly "ARKA_MITRE" nil (list (239.045457 388.722856 -0.035226) (251.386322 397.22764 0.0) (243.886322 410.218021 0.0)))
  (ar:poly "ARKA_MITRE" nil (list (35.501754 304.5 0.0) (20.501754 304.5 0.013159) (20.949005 289.508401 0.0)))
  (ar:poly "ARKA_MITRE" nil (list (149.375372 67.067409 0.013159) (162.134852 59.184279 0.0) (169.634852 72.17466 0.0)))
  (ar:poly "ARKA_MITRE" nil (list (243.886322 200.781979 0.0) (251.386322 213.77236 -0.035226) (239.045457 222.277144 0.0)))
  (ar:poly "ARKA_MITRE" nil (list (200.199621 289.560106 -0.035226) (199.004695 304.5 0.0) (184.004695 304.5 0.0)))
  (ar:poly "ARKA_MITRE" nil (list (171.366903 71.17466 0.0) (163.866903 58.184279 0.013159) (177.073633 51.07581 0.0)))
  (ar:poly "ARKA_MITRE" nil (list (433.926367 51.07581 0.013159) (447.133097 58.184279 0.0) (439.633097 71.17466 0.0)))
  (ar:poly "ARKA_MITRE" nil (list (365.381627 199.781979 0.0) (357.881627 212.77236 -0.035226) (344.345836 206.33725 0.0)))
  (ar:poly "ARKA_MITRE" nil (list (266.654164 206.33725 -0.035226) (253.118373 212.77236 0.0) (245.618373 199.781979 0.0)))
  (ar:poly "ARKA_MITRE" nil (list (441.365148 72.17466 0.0) (448.865148 59.184279 0.013159) (461.624628 67.067409 0.0)))
  (ar:poly "ARKA_MITRE" nil (list (590.050995 289.508401 0.013159) (590.498246 304.5 0.0) (575.498246 304.5 0.0)))
  (ar:poly "ARKA_MITRE" nil (list (426.995305 304.5 0.0) (411.995305 304.5 -0.035226) (410.800379 289.560106 0.0)))
  (ar:poly "ARKA_MITRE" nil (list (371.954543 222.277144 -0.035226) (359.613678 213.77236 0.0) (367.113678 200.781979 0.0)))
  (ar:point "ARKA_CENTRE" 305.5 305.5)
  (ar:point "ARKA_CENTRE" 305.5 305.5)
  (ar:poly "ARKA_SECTION" nil (list (698.5 12.5 -0.414214) (706.5 20.5 0.0) (706.5 26.5 0.0)))
  (ar:text "ARKA_INFO_NO_CUT" 694.5 -6.5 15.0 "START")
  (ar:text "ARKA_INFO_NO_CUT" 718.5 16.5 15.0 "SECTION R8 + 6 (VERBATIM)")
  (ar:text "ARKA_INFO_NO_CUT" 698.5 576.5 15.0 "CIR - TRACERY FULL")
  (ar:text "ARKA_INFO_NO_CUT" 698.5 554.5 15.0 "PATTERN SUNBURST SPOKES 6 RINGS 2 PANES 7")
  (ar:text "ARKA_INFO_NO_CUT" 698.5 532.5 15.0 "TIMBER BAR 22 EDGE MARGIN 18 PANE +2 LIMIT +10 MITRE LEG 15")
  (ar:text "ARKA_INFO_NO_CUT" 698.5 510.5 15.0 "ARKA_PANE = MOULDING RAIL (INNER EDGE OF THE BEAD), ARKA_FRONT_HINGES_3MM = BEAD LIMIT (NOT DRILLING)")
  (ar:text "ARKA_INFO_NO_CUT" 698.5 488.5 15.0 "NOT A TOOLPATH")
  (princ "\nARKA: tracery drawn. Layers ARKA_*; ARKA_INFO_NO_CUT is not a toolpath.")
  (princ)
)
(princ "\nARKA loaded - type ARKA to draw the tracery.")
(princ)
