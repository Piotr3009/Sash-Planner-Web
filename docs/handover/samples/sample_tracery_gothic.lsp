;;; ARKA tracery — generated by Production Core (ARCHED-WINDOWS-v3 Block 0.4)
;;; window gothic - pattern intersecting - units mm - layers ARKA_*
;;; The DXF of the same name carries the same entities; ARKA_INFO_NO_CUT is never machined.
(defun ar:layer (name col)
  (if (not (tblsearch "LAYER" name))
    (command "_.-LAYER" "_M" name "_C" (itoa col) name "")
    (command "_.-LAYER" "_S" name ""))
)
(defun ar:poly (layer closed verts / data v)
  (setq data (list (quote (0 . "LWPOLYLINE")) (quote (100 . "AcDbEntity")) (cons 8 layer)
                   (quote (100 . "AcDbPolyline")) (cons 90 (length verts)) (cons 70 (if closed 1 0))))
  (foreach v verts
    (setq data (append data (list (cons 10 (list (+ (car *ar-ip*) (car v)) (+ (cadr *ar-ip*) (cadr v)))) (cons 42 (caddr v))))))
  (entmake data)
)
(defun ar:point (layer x y)
  (entmake (list (quote (0 . "POINT")) (cons 8 layer) (cons 10 (list (+ (car *ar-ip*) x) (+ (cadr *ar-ip*) y) 0.0))))
)
(defun ar:text (layer x y h str)
  (entmake (list (quote (0 . "TEXT")) (cons 8 layer) (cons 10 (list (+ (car *ar-ip*) x) (+ (cadr *ar-ip*) y) 0.0)) (cons 40 h) (cons 1 str)))
)
(defun c:ARKA ( / ip)
  (setq ip (getpoint "\nInsertion point <0,0>: "))
  (setq *ar-ip* (if ip (list (car ip) (cadr ip)) (list 0.0 0.0)))
  (ar:layer "ARKA_OUTLINE" 7)
  (ar:layer "ARKA_PANE" 3)
  (ar:layer "ARKA_FRONT_HINGES_3MM" 50)
  (ar:layer "ARKA_MITRE" 1)
  (ar:layer "ARKA_SECTION" 5)
  (ar:layer "ARKA_PANE_ZEWN_REF" 3)
  (ar:layer "ARKA_CENTRE" 6)
  (ar:layer "ARKA_INFO_NO_CUT" 8)
  (ar:poly "ARKA_OUTLINE" T (list (12.5 12.5 0.0) (798.5 12.5 0.0) (798.5 1032.474585 0.249098) (405.5 1772.372562 0.249098) (12.5 1032.474596 0.0)))
  (ar:poly "ARKA_PANE_ZEWN_REF" T (list (14.5 14.5 0.0) (796.5 14.5 0.0) (796.5 1032.474585 0.248695) (405.5 1769.957477 0.248695) (14.5 1032.474596 0.0)))
  (ar:poly "ARKA_OUTLINE" T (list (30.5 30.5 0.0) (259.333333 30.5 0.0) (259.333333 505.237298 0.0) (30.5 505.237298 0.0)))
  (ar:poly "ARKA_PANE" T (list (28.5 28.5 0.0) (261.333333 28.5 0.0) (261.333333 507.237298 0.0) (28.5 507.237298 0.0)))
  (ar:poly "ARKA_FRONT_HINGES_3MM" T (list (20.5 20.5 0.0) (269.333333 20.5 0.0) (269.333333 515.237298 0.0) (20.5 515.237298 0.0)))
  (ar:poly "ARKA_OUTLINE" T (list (281.333333 30.5 0.0) (529.666667 30.5 0.0) (529.666667 505.237298 0.0) (281.333333 505.237298 0.0)))
  (ar:poly "ARKA_PANE" T (list (279.333333 28.5 0.0) (531.666667 28.5 0.0) (531.666667 507.237298 0.0) (279.333333 507.237298 0.0)))
  (ar:poly "ARKA_FRONT_HINGES_3MM" T (list (271.333333 20.5 0.0) (539.666667 20.5 0.0) (539.666667 515.237298 0.0) (271.333333 515.237298 0.0)))
  (ar:poly "ARKA_OUTLINE" T (list (551.666667 30.5 0.0) (780.5 30.5 0.0) (780.5 505.237298 0.0) (551.666667 505.237298 0.0)))
  (ar:poly "ARKA_PANE" T (list (549.666667 28.5 0.0) (782.5 28.5 0.0) (782.5 507.237298 0.0) (549.666667 507.237298 0.0)))
  (ar:poly "ARKA_FRONT_HINGES_3MM" T (list (541.666667 20.5 0.0) (790.5 20.5 0.0) (790.5 515.237298 0.0) (541.666667 515.237298 0.0)))
  (ar:poly "ARKA_OUTLINE" T (list (780.5 527.237298 0.0) (780.5 1032.474596 0.089172) (725.713486 1337.228328 0.265434) (551.666667 1032.474596 0.0) (529.666667 516.237298 0.0) (529.666667 1530.805142 0.061674) (419.473667 1424.089753 -0.123958) (543.640333 1134.004277 -0.195945) (717.687153 1358.015729 0.071313) (593.520486 1573.078713 0.019832) (551.666667 1546.659388 0.0) (551.666667 527.237298 0.0)))
  (ar:poly "ARKA_PANE" T (list (782.5 525.237298 0.0) (782.5 1032.474596 0.089856) (726.755819 1340.156053 0.267229) (549.666667 1032.474596 0.0) (531.666667 516.237298 0.0) (531.666667 1534.80251 0.063908) (416.933 1424.121096 -0.128351) (543.099667 1124.220765 -0.203803) (720.188819 1357.145395 0.072307) (594.022153 1575.674601 0.020944) (549.666667 1547.709818 0.0) (549.666667 525.237298 0.0)))
  (ar:poly "ARKA_FRONT_HINGES_3MM" T (list (790.5 517.237298 0.0) (790.5 1032.474596 0.092516) (730.925153 1351.689754 0.274161) (541.666667 1032.474596 0.0) (539.666667 516.237298 0.0) (539.666667 1550.483605 0.072657) (406.770333 1424.183775 -0.15508) (540.937 1062.935174 -0.25207) (730.195486 1353.570151 0.076254) (596.028819 1586.004134 0.025317) (541.666667 1551.890294 0.0) (541.666667 517.237298 0.0)))
  (ar:poly "ARKA_OUTLINE" T (list (579.546819 1590.404596 0.012142) (551.666667 1622.469205 0.0) (551.666667 1573.153182 -0.012687)))
  (ar:poly "ARKA_PANE" T (list (582.589153 1589.860709 0.01428) (549.666667 1627.60341 0.0) (549.666667 1569.441386 -0.015039)))
  (ar:poly "ARKA_FRONT_HINGES_3MM" T (list (594.758486 1587.585161 0.02267) (541.666667 1647.711926 0.0) (541.666667 1554.33026 -0.024634)))
  (ar:poly "ARKA_OUTLINE" T (list (529.666667 1645.696393 0.046533) (405.5 1750.544927 0.046533) (281.333333 1645.696393 0.0) (281.333333 1558.09867 -0.066114) (405.5 1441.780547 -0.066114) (529.666667 1558.09867 0.0)))
  (ar:poly "ARKA_PANE" T (list (531.666667 1646.513932 0.047164) (405.5 1752.980668 0.047164) (279.333333 1646.513932 0.0) (279.333333 1557.069043 -0.067469) (405.5 1438.615821 -0.067469) (531.666667 1557.069043 0.0)))
  (ar:poly "ARKA_FRONT_HINGES_3MM" T (list (539.666667 1649.773259 0.04966) (405.5 1762.697165 0.04966) (271.333333 1649.773259 0.0) (271.333333 1552.930166 -0.073021) (405.5 1425.80401 -0.073021) (539.666667 1552.930166 0.0)))
  (ar:poly "ARKA_OUTLINE" T (list (259.333333 1622.469205 0.012142) (231.453181 1590.404596 -0.012687) (259.333333 1573.153182 0.0)))
  (ar:poly "ARKA_PANE" T (list (261.333333 1627.60341 0.01428) (228.410847 1589.860709 -0.015039) (261.333333 1569.441386 0.0)))
  (ar:poly "ARKA_FRONT_HINGES_3MM" T (list (269.333333 1647.711926 0.02267) (216.241514 1587.585161 -0.024634) (269.333333 1554.33026 0.0)))
  (ar:poly "ARKA_OUTLINE" T (list (217.479514 1573.078713 0.071313) (93.312847 1358.015729 -0.195945) (267.359667 1134.004277 -0.123958) (391.526333 1424.089753 0.061674) (281.333333 1530.805142 0.0) (281.333333 527.237298 0.0) (529.666667 527.237298 0.0) (529.666667 1032.474596 0.16182) (405.5 1406.084055 0.16182) (281.333333 1032.474596 0.0) (259.333333 516.237298 0.0) (259.333333 1546.659388 0.019832)))
  (ar:poly "ARKA_PANE" T (list (216.977847 1575.674601 0.072307) (90.811181 1357.145395 -0.203803) (267.900333 1124.220765 -0.128351) (394.067 1424.121096 0.063908) (279.333333 1534.80251 0.0) (279.333333 525.237298 0.0) (531.666667 525.237298 0.0) (531.666667 1032.474596 0.162914) (405.5 1409.415831 0.162914) (279.333333 1032.474596 0.0) (261.333333 516.237298 0.0) (261.333333 1547.709818 0.020944)))
  (ar:poly "ARKA_FRONT_HINGES_3MM" T (list (214.971181 1586.004134 0.076254) (80.804514 1353.570151 -0.25207) (270.063 1062.935174 -0.15508) (404.229667 1424.183775 0.072657) (271.333333 1550.483605 0.0) (271.333333 517.237298 0.0) (539.666667 517.237298 0.0) (539.666667 1032.474589 0.167165) (405.5 1422.560947 0.167165) (271.333333 1032.474596 0.0) (269.333333 516.237298 0.0) (269.333333 1551.890294 0.025317)))
  (ar:poly "ARKA_OUTLINE" T (list (85.286514 1337.228328 0.089172) (30.5 1032.474596 0.0) (30.5 527.237298 0.0) (259.333333 527.237298 0.0) (259.333333 1032.474596 0.265434)))
  (ar:poly "ARKA_PANE" T (list (84.244181 1340.156053 0.089856) (28.5 1032.474596 0.0) (28.5 525.237298 0.0) (261.333333 525.237298 0.0) (261.333333 1032.474596 0.267229)))
  (ar:poly "ARKA_FRONT_HINGES_3MM" T (list (80.074847 1351.689754 0.092516) (20.5 1032.474596 0.0) (20.5 517.237298 0.0) (269.333333 517.237298 0.0) (269.333333 1032.474596 0.274161)))
  (ar:poly "ARKA_MITRE" nil (list (20.5 35.5 0.0) (20.5 20.5 0.0) (35.5 20.5 0.0)))
  (ar:poly "ARKA_MITRE" nil (list (254.333333 20.5 0.0) (269.333333 20.5 0.0) (269.333333 35.5 0.0)))
  (ar:poly "ARKA_MITRE" nil (list (269.333333 500.237298 0.0) (269.333333 515.237298 0.0) (254.333333 515.237298 0.0)))
  (ar:poly "ARKA_MITRE" nil (list (35.5 515.237298 0.0) (20.5 515.237298 0.0) (20.5 500.237298 0.0)))
  (ar:poly "ARKA_MITRE" nil (list (271.333333 35.5 0.0) (271.333333 20.5 0.0) (286.333333 20.5 0.0)))
  (ar:poly "ARKA_MITRE" nil (list (524.666667 20.5 0.0) (539.666667 20.5 0.0) (539.666667 35.5 0.0)))
  (ar:poly "ARKA_MITRE" nil (list (539.666667 500.237298 0.0) (539.666667 515.237298 0.0) (524.666667 515.237298 0.0)))
  (ar:poly "ARKA_MITRE" nil (list (286.333333 515.237298 0.0) (271.333333 515.237298 0.0) (271.333333 500.237298 0.0)))
  (ar:poly "ARKA_MITRE" nil (list (541.666667 35.5 0.0) (541.666667 20.5 0.0) (556.666667 20.5 0.0)))
  (ar:poly "ARKA_MITRE" nil (list (775.5 20.5 0.0) (790.5 20.5 0.0) (790.5 35.5 0.0)))
  (ar:poly "ARKA_MITRE" nil (list (790.5 500.237298 0.0) (790.5 515.237298 0.0) (775.5 515.237298 0.0)))
  (ar:poly "ARKA_MITRE" nil (list (556.666667 515.237298 0.0) (541.666667 515.237298 0.0) (541.666667 500.237298 0.0)))
  (ar:poly "ARKA_MITRE" nil (list (775.5 517.237298 0.0) (790.5 517.237298 0.0) (790.5 532.237298 0.0)))
  (ar:poly "ARKA_MITRE" nil (list (736.216761 1337.654317 0.004237) (730.925153 1351.689754 0.010307) (717.916727 1344.223229 0.0)))
  (ar:poly "ARKA_MITRE" nil (list (539.724779 531.237186 0.0) (539.666667 516.237298 0.0) (539.666667 531.237298 0.0)))
  (ar:poly "ARKA_MITRE" nil (list (539.666667 1535.483605 0.0) (539.666667 1550.483605 0.005913) (527.517628 1541.686426 0.0)))
  (ar:poly "ARKA_MITRE" nil (list (416.174106 1435.869602 0.005913) (406.770333 1424.183775 -0.005895) (415.866145 1412.256672 0.0)))
  (ar:poly "ARKA_MITRE" nil (list (540.042215 1077.908114 -0.005895) (540.937 1062.935174 -0.010251) (542.492009 1077.853298 0.0)))
  (ar:poly "ARKA_MITRE" nil (list (717.180865 1346.114407 -0.010251) (730.195486 1353.570151 0.004237) (724.634995 1367.501251 0.0)))
  (ar:poly "ARKA_MITRE" nil (list (605.311044 1574.221311 0.004237) (596.028819 1586.004134 0.005913) (583.023923 1578.530034 0.0)))
  (ar:poly "ARKA_MITRE" nil (list (554.053078 1560.349981 0.005913) (541.666667 1551.890294 0.0) (541.666667 1536.890294 0.0)))
  (ar:poly "ARKA_MITRE" nil (list (541.666667 532.237298 0.0) (541.666667 517.237298 0.0) (556.666667 517.237298 0.0)))
  (ar:poly "ARKA_MITRE" nil (list (581.757274 1580.104649 -0.005895) (594.758486 1587.585161 0.004237) (585.251282 1599.187217 0.0)))
  (ar:poly "ARKA_MITRE" nil (list (552.002544 1636.841588 0.004237) (541.666667 1647.711926 0.0) (541.666667 1632.711926 0.0)))
  (ar:poly "ARKA_MITRE" nil (list (541.666667 1569.33026 0.0) (541.666667 1554.33026 -0.005895) (554.071352 1562.763134 0.0)))
  (ar:poly "ARKA_MITRE" nil (list (539.666667 1634.773259 0.0) (539.666667 1649.773259 0.004237) (529.113391 1660.432667 0.0)))
  (ar:poly "ARKA_MITRE" nil (list (417.804244 1754.11811 0.004237) (405.5 1762.697165 0.004237) (393.195756 1754.11811 0.0)))
  (ar:poly "ARKA_MITRE" nil (list (281.886609 1660.432667 0.004237) (271.333333 1649.773259 0.0) (271.333333 1634.773259 0.0)))
  (ar:poly "ARKA_MITRE" nil (list (271.333333 1567.930166 0.0) (271.333333 1552.930166 -0.005895) (283.502187 1544.160412 0.0)))
  (ar:poly "ARKA_MITRE" nil (list (396.08767 1437.482949 -0.005895) (405.5 1425.80401 -0.005895) (414.91233 1437.482949 0.0)))
  (ar:poly "ARKA_MITRE" nil (list (527.497813 1544.160412 -0.005895) (539.666667 1552.930166 0.0) (539.666667 1567.930166 0.0)))
  (ar:poly "ARKA_MITRE" nil (list (269.333333 1632.711926 0.0) (269.333333 1647.711926 0.004237) (258.997456 1636.841588 0.0)))
  (ar:poly "ARKA_MITRE" nil (list (225.748718 1599.187217 0.004237) (216.241514 1587.585161 -0.005895) (229.242726 1580.104649 0.0)))
  (ar:poly "ARKA_MITRE" nil (list (256.928648 1562.763134 -0.005895) (269.333333 1554.33026 0.0) (269.333333 1569.33026 0.0)))
  (ar:poly "ARKA_MITRE" nil (list (227.976077 1578.530034 0.005913) (214.971181 1586.004134 0.004237) (205.688956 1574.221311 0.0)))
  (ar:poly "ARKA_MITRE" nil (list (86.365005 1367.501251 0.004237) (80.804514 1353.570151 -0.010251) (93.819135 1346.114407 0.0)))
  (ar:poly "ARKA_MITRE" nil (list (268.507991 1077.853298 -0.010251) (270.063 1062.935174 -0.005895) (270.957785 1077.908114 0.0)))
  (ar:poly "ARKA_MITRE" nil (list (395.133855 1412.256672 -0.005895) (404.229667 1424.183775 0.005913) (394.825894 1435.869602 0.0)))
  (ar:poly "ARKA_MITRE" nil (list (283.482372 1541.686426 0.005913) (271.333333 1550.483605 0.0) (271.333333 1535.483605 0.0)))
  (ar:poly "ARKA_MITRE" nil (list (271.333333 532.237298 0.0) (271.333333 517.237298 0.0) (286.333333 517.237298 0.0)))
  (ar:poly "ARKA_MITRE" nil (list (524.666667 517.237298 0.0) (539.666667 517.237298 0.0) (539.666667 532.237298 0.0)))
  (ar:poly "ARKA_MITRE" nil (list (414.586026 1410.62639 0.005913) (405.5 1422.560947 0.005913) (396.413974 1410.62639 0.0)))
  (ar:poly "ARKA_MITRE" nil (list (269.391446 531.237186 0.0) (269.333333 516.237298 0.0) (269.333333 531.237298 0.0)))
  (ar:poly "ARKA_MITRE" nil (list (269.333333 1536.890294 0.0) (269.333333 1551.890294 0.005913) (256.946922 1560.349981 0.0)))
  (ar:poly "ARKA_MITRE" nil (list (93.083273 1344.223229 0.010307) (80.074847 1351.689754 0.004237) (74.783239 1337.654317 0.0)))
  (ar:poly "ARKA_MITRE" nil (list (20.5 532.237298 0.0) (20.5 517.237298 0.0) (35.5 517.237298 0.0)))
  (ar:poly "ARKA_MITRE" nil (list (254.333333 517.237298 0.0) (269.333333 517.237298 0.0) (269.333333 532.237298 0.0)))
  (ar:point "ARKA_CENTRE" -94.5 1032.474596)
  (ar:point "ARKA_CENTRE" 905.5 1032.474596)
  (ar:poly "ARKA_SECTION" nil (list (898.5 12.5 -0.414214) (906.5 20.5 0.0) (906.5 26.5 0.0)))
  (ar:text "ARKA_INFO_NO_CUT" 894.5 -6.5 15.0 "START")
  (ar:text "ARKA_INFO_NO_CUT" 918.5 16.5 15.0 "SECTION R8 + 6 (VERBATIM)")
  (ar:text "ARKA_INFO_NO_CUT" 898.5 1750.372562 15.0 "gothic - TRACERY FULL")
  (ar:text "ARKA_INFO_NO_CUT" 898.5 1728.372562 15.0 "PATTERN INTERSECTING SPOKES 0 RINGS 0 PANES 9")
  (ar:text "ARKA_INFO_NO_CUT" 898.5 1706.372562 15.0 "TIMBER BAR 22 EDGE MARGIN 18 PANE +2 LIMIT +10 MITRE LEG 15")
  (ar:text "ARKA_INFO_NO_CUT" 898.5 1684.372562 15.0 "ARKA_PANE = MOULDING RAIL (INNER EDGE OF THE BEAD), ARKA_FRONT_HINGES_3MM = BEAD LIMIT (NOT DRILLING)")
  (ar:text "ARKA_INFO_NO_CUT" 898.5 1662.372562 15.0 "NOT A TOOLPATH")
  (princ "\nARKA: tracery drawn. Layers ARKA_*; ARKA_INFO_NO_CUT is not a toolpath.")
  (princ)
)
(princ "\nARKA loaded - type ARKA to draw the tracery.")
(princ)
