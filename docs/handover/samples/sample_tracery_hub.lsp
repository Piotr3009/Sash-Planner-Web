;;; ARKA tracery — generated by Production Core (ARCHED-WINDOWS-v3 Block 0.4)
;;; window hub - pattern hub-spoke - units mm - layers ARKA_*
;;; The DXF of the same name carries the same entities; ARKA_INFO_NO_CUT is never machined.
(defun ar:layer (name col)
  (if (not (tblsearch "LAYER" name))
    (command "_.-LAYER" "_M" name "_C" (itoa col) name "")
    (command "_.-LAYER" "_S" name ""))
)
(defun ar:poly (layer closed verts / data v)
  (setq data (list (quote (0 . "LWPOLYLINE")) (quote (100 . "AcDbEntity")) (cons 8 layer)
                   (quote (100 . "AcDbPolyline")) (cons 90 (length verts)) (cons 70 (if closed 1 0))))
  (foreach v verts
    (setq data (append data (list (cons 10 (list (+ (car *ar-ip*) (car v)) (+ (cadr *ar-ip*) (cadr v)))) (cons 42 (caddr v))))))
  (entmake data)
)
(defun ar:point (layer x y)
  (entmake (list (quote (0 . "POINT")) (cons 8 layer) (cons 10 (list (+ (car *ar-ip*) x) (+ (cadr *ar-ip*) y) 0.0))))
)
(defun ar:text (layer x y h str)
  (entmake (list (quote (0 . "TEXT")) (cons 8 layer) (cons 10 (list (+ (car *ar-ip*) x) (+ (cadr *ar-ip*) y) 0.0)) (cons 40 h) (cons 1 str)))
)
(defun c:ARKA ( / ip)
  (setq ip (getpoint "\nInsertion point <0,0>: "))
  (setq *ar-ip* (if ip (list (car ip) (cadr ip)) (list 0.0 0.0)))
  (ar:layer "ARKA_OUTLINE" 7)
  (ar:layer "ARKA_PANE" 3)
  (ar:layer "ARKA_FRONT_HINGES_3MM" 50)
  (ar:layer "ARKA_MITRE" 1)
  (ar:layer "ARKA_SECTION" 5)
  (ar:layer "ARKA_PANE_ZEWN_REF" 3)
  (ar:layer "ARKA_CENTRE" 6)
  (ar:layer "ARKA_INFO_NO_CUT" 8)
  (ar:poly "ARKA_OUTLINE" T (list (12.5 12.5 0.0) (798.5 12.5 0.0) (798.5 898.5 1.0) (12.5 898.5 0.0)))
  (ar:poly "ARKA_PANE_ZEWN_REF" T (list (14.5 14.5 0.0) (796.5 14.5 0.0) (796.5 898.5 1.0) (14.5 898.5 0.0)))
  (ar:poly "ARKA_OUTLINE" T (list (30.5 30.5 0.0) (272.85 30.5 0.0) (272.85 887.5 0.0) (30.5 887.5 0.0)))
  (ar:poly "ARKA_PANE" T (list (28.5 28.5 0.0) (274.85 28.5 0.0) (274.85 889.5 0.0) (28.5 889.5 0.0)))
  (ar:poly "ARKA_FRONT_HINGES_3MM" T (list (20.5 20.5 0.0) (282.85 20.5 0.0) (282.85 897.5 0.0) (20.5 897.5 0.0)))
  (ar:poly "ARKA_OUTLINE" T (list (294.85 30.5 0.0) (516.15 30.5 0.0) (516.15 898.5 1.0) (294.85 898.500002 0.0)))
  (ar:poly "ARKA_PANE" T (list (292.85 28.5 0.0) (518.15 28.5 0.0) (518.15 898.5 1.0) (292.85 898.500001 0.0)))
  (ar:poly "ARKA_FRONT_HINGES_3MM" T (list (284.85 20.5 0.0) (526.15 20.5 0.0) (526.15 898.5 1.0) (284.85 898.500002 0.0)))
  (ar:poly "ARKA_OUTLINE" T (list (538.15 30.5 0.0) (780.5 30.5 0.0) (780.5 887.5 0.0) (538.15 887.5 0.0)))
  (ar:poly "ARKA_PANE" T (list (536.15 28.5 0.0) (782.5 28.5 0.0) (782.5 889.5 0.0) (536.15 889.5 0.0)))
  (ar:poly "ARKA_FRONT_HINGES_3MM" T (list (528.15 20.5 0.0) (790.5 20.5 0.0) (790.5 897.5 0.0) (528.15 897.5 0.0)))
  (ar:poly "ARKA_OUTLINE" T (list (780.338632 909.5 0.252288) (602.445595 1217.619778 0.0) (481.122842 1007.482605 -0.223923) (537.693126 909.5 0.0)))
  (ar:poly "ARKA_PANE" T (list (782.392558 907.5 0.255195) (601.740507 1220.398529 0.0) (478.46405 1006.877442 -0.231328) (535.839643 907.5 0.0)))
  (ar:poly "ARKA_FRONT_HINGES_3MM" T (list (790.498701 899.5 0.266558) (598.865376 1231.418656 0.0) (467.688987 1004.214485 -0.263585) (528.145923 899.5 0.0)))
  (ar:poly "ARKA_OUTLINE" T (list (583.393037 1228.619778 0.252288) (227.606963 1228.619778 0.0) (348.929717 1018.482605 -0.223923) (462.070283 1018.482605 0.0)))
  (ar:poly "ARKA_PANE" T (list (586.15205 1229.398529 0.255195) (224.84795 1229.398529 0.0) (348.124407 1015.877442 -0.231328) (462.875593 1015.877442 0.0)))
  (ar:poly "ARKA_FRONT_HINGES_3MM" T (list (597.133325 1232.418656 0.266558) (213.866675 1232.418656 0.0) (345.043064 1005.214485 -0.263585) (465.956936 1005.214485 0.0)))
  (ar:poly "ARKA_OUTLINE" T (list (208.554405 1217.619778 0.252288) (30.661368 909.5 0.0) (273.306874 909.5 -0.223923) (329.877158 1007.482605 0.0)))
  (ar:poly "ARKA_PANE" T (list (209.259493 1220.398529 0.255195) (28.607442 907.5 0.0) (275.160357 907.5 -0.231328) (332.53595 1006.877442 0.0)))
  (ar:poly "ARKA_FRONT_HINGES_3MM" T (list (212.134624 1231.418656 0.266558) (20.501299 899.5 0.0) (282.854077 899.5 -0.263585) (343.311013 1004.214485 0.0)))
  (ar:poly "ARKA_MITRE" nil (list (20.5 35.5 0.0) (20.5 20.5 0.0) (35.5 20.5 0.0)))
  (ar:poly "ARKA_MITRE" nil (list (267.85 20.5 0.0) (282.85 20.5 0.0) (282.85 35.5 0.0)))
  (ar:poly "ARKA_MITRE" nil (list (282.85 882.5 0.0) (282.85 897.5 0.0) (267.85 897.5 0.0)))
  (ar:poly "ARKA_MITRE" nil (list (35.5 897.5 0.0) (20.5 897.5 0.0) (20.5 882.5 0.0)))
  (ar:poly "ARKA_MITRE" nil (list (284.85 35.5 0.0) (284.85 20.5 0.0) (299.85 20.5 0.0)))
  (ar:poly "ARKA_MITRE" nil (list (511.15 20.5 0.0) (526.15 20.5 0.0) (526.15 35.5 0.0)))
  (ar:poly "ARKA_MITRE" nil (list (528.15 35.5 0.0) (528.15 20.5 0.0) (543.15 20.5 0.0)))
  (ar:poly "ARKA_MITRE" nil (list (775.5 20.5 0.0) (790.5 20.5 0.0) (790.5 35.5 0.0)))
  (ar:poly "ARKA_MITRE" nil (list (790.5 882.5 0.0) (790.5 897.5 0.0) (775.5 897.5 0.0)))
  (ar:poly "ARKA_MITRE" nil (list (543.15 897.5 0.0) (528.15 897.5 0.0) (528.15 882.5 0.0)))
  (ar:poly "ARKA_MITRE" nil (list (775.498701 899.5 0.0) (790.498701 899.5 0.009741) (790.16758 914.495396 0.0)))
  (ar:poly "ARKA_MITRE" nil (list (611.686209 1223.634199 0.009741) (598.865376 1231.418656 0.0) (591.365376 1218.428275 0.0)))
  (ar:poly "ARKA_MITRE" nil (list (475.188987 1017.204866 0.0) (467.688987 1004.214485 -0.030584) (480.121077 995.83816 0.0)))
  (ar:poly "ARKA_MITRE" nil (list (527.107858 914.454669 -0.030584) (528.145923 899.5 0.0) (543.145923 899.5 0.0)))
  (ar:poly "ARKA_MITRE" nil (list (589.633325 1219.428275 0.0) (597.133325 1232.418656 0.009741) (583.981371 1239.629594 0.0)))
  (ar:poly "ARKA_MITRE" nil (list (227.018629 1239.629594 0.009741) (213.866675 1232.418656 0.0) (221.366675 1219.428275 0.0)))
  (ar:poly "ARKA_MITRE" nil (list (337.543064 1018.204866 0.0) (345.043064 1005.214485 -0.030584) (358.51322 1011.792828 0.0)))
  (ar:poly "ARKA_MITRE" nil (list (452.48678 1011.792828 -0.030584) (465.956936 1005.214485 0.0) (473.456936 1018.204866 0.0)))
  (ar:poly "ARKA_MITRE" nil (list (219.634624 1218.428275 0.0) (212.134624 1231.418656 0.009741) (199.313791 1223.634199 0.0)))
  (ar:poly "ARKA_MITRE" nil (list (20.83242 914.495396 0.009741) (20.501299 899.5 0.0) (35.501299 899.5 0.0)))
  (ar:poly "ARKA_MITRE" nil (list (267.854077 899.5 0.0) (282.854077 899.5 -0.030584) (283.892142 914.454669 0.0)))
  (ar:poly "ARKA_MITRE" nil (list (330.878923 995.83816 -0.030584) (343.311013 1004.214485 0.0) (335.811013 1017.204866 0.0)))
  (ar:point "ARKA_CENTRE" 405.5 898.5)
  (ar:poly "ARKA_SECTION" nil (list (898.5 12.5 -0.414214) (906.5 20.5 0.0) (906.5 26.5 0.0)))
  (ar:text "ARKA_INFO_NO_CUT" 894.5 -6.5 15.0 "START")
  (ar:text "ARKA_INFO_NO_CUT" 918.5 16.5 15.0 "SECTION R8 + 6 (VERBATIM)")
  (ar:text "ARKA_INFO_NO_CUT" 898.5 1269.5 15.0 "hub - TRACERY FULL")
  (ar:text "ARKA_INFO_NO_CUT" 898.5 1247.5 15.0 "PATTERN HUB-SPOKE SPOKES 4 RINGS 1 PANES 6")
  (ar:text "ARKA_INFO_NO_CUT" 898.5 1225.5 15.0 "TIMBER BAR 22 EDGE MARGIN 18 PANE +2 LIMIT +10 MITRE LEG 15")
  (ar:text "ARKA_INFO_NO_CUT" 898.5 1203.5 15.0 "ARKA_PANE = MOULDING RAIL (INNER EDGE OF THE BEAD), ARKA_FRONT_HINGES_3MM = BEAD LIMIT (NOT DRILLING)")
  (ar:text "ARKA_INFO_NO_CUT" 898.5 1181.5 15.0 "NOT A TOOLPATH")
  (princ "\nARKA: tracery drawn. Layers ARKA_*; ARKA_INFO_NO_CUT is not a toolpath.")
  (princ)
)
(princ "\nARKA loaded - type ARKA to draw the tracery.")
(princ)
