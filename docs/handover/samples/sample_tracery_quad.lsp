;;; ARKA tracery — generated by Production Core (ARCHED-WINDOWS-v3 Block 0.4)
;;; window quad - pattern quad-hub-spoke - units mm - layers ARKA_*
;;; The DXF of the same name carries the same entities; ARKA_INFO_NO_CUT is never machined.
(defun ar:layer (name col)
  (if (not (tblsearch "LAYER" name))
    (command "_.-LAYER" "_M" name "_C" (itoa col) name "")
    (command "_.-LAYER" "_S" name ""))
)
(defun ar:poly (layer closed verts / data v)
  (setq data (list (quote (0 . "LWPOLYLINE")) (quote (100 . "AcDbEntity")) (cons 8 layer)
                   (quote (100 . "AcDbPolyline")) (cons 90 (length verts)) (cons 70 (if closed 1 0))))
  (foreach v verts
    (setq data (append data (list (cons 10 (list (+ (car *ar-ip*) (car v)) (+ (cadr *ar-ip*) (cadr v)))) (cons 42 (caddr v))))))
  (entmake data)
)
(defun ar:point (layer x y)
  (entmake (list (quote (0 . "POINT")) (cons 8 layer) (cons 10 (list (+ (car *ar-ip*) x) (+ (cadr *ar-ip*) y) 0.0))))
)
(defun ar:text (layer x y h str)
  (entmake (list (quote (0 . "TEXT")) (cons 8 layer) (cons 10 (list (+ (car *ar-ip*) x) (+ (cadr *ar-ip*) y) 0.0)) (cons 40 h) (cons 1 str)))
)
(defun c:ARKA ( / ip)
  (setq ip (getpoint "\nInsertion point <0,0>: "))
  (setq *ar-ip* (if ip (list (car ip) (cadr ip)) (list 0.0 0.0)))
  (ar:layer "ARKA_OUTLINE" 7)
  (ar:layer "ARKA_PANE" 3)
  (ar:layer "ARKA_FRONT_HINGES_3MM" 50)
  (ar:layer "ARKA_MITRE" 1)
  (ar:layer "ARKA_SECTION" 5)
  (ar:layer "ARKA_PANE_ZEWN_REF" 3)
  (ar:layer "ARKA_CENTRE" 6)
  (ar:layer "ARKA_INFO_NO_CUT" 8)
  (ar:poly "ARKA_OUTLINE" T (list (12.5 12.5 0.0) (798.5 12.5 0.0) (798.5 898.5 1.0) (12.5 898.5 0.0)))
  (ar:poly "ARKA_PANE_ZEWN_REF" T (list (14.5 14.5 0.0) (796.5 14.5 0.0) (796.5 898.5 1.0) (14.5 898.5 0.0)))
  (ar:poly "ARKA_OUTLINE" T (list (30.5 30.5 0.0) (124.166667 30.5 0.0) (124.166667 887.5 0.0) (30.5 887.5 0.0)))
  (ar:poly "ARKA_PANE" T (list (28.5 28.5 0.0) (126.166667 28.5 0.0) (126.166667 889.5 0.0) (28.5 889.5 0.0)))
  (ar:poly "ARKA_FRONT_HINGES_3MM" T (list (20.5 20.5 0.0) (134.166667 20.5 0.0) (134.166667 897.5 0.0) (20.5 897.5 0.0)))
  (ar:poly "ARKA_OUTLINE" T (list (146.166667 30.5 0.0) (259.333333 30.5 0.0) (259.333333 887.5 0.0) (146.166667 887.5 0.0)))
  (ar:poly "ARKA_PANE" T (list (144.166667 28.5 0.0) (261.333333 28.5 0.0) (261.333333 889.5 0.0) (144.166667 889.5 0.0)))
  (ar:poly "ARKA_FRONT_HINGES_3MM" T (list (136.166667 20.5 0.0) (269.333333 20.5 0.0) (269.333333 897.5 0.0) (136.166667 897.5 0.0)))
  (ar:poly "ARKA_OUTLINE" T (list (281.333333 30.5 0.0) (529.666667 30.5 0.0) (529.666667 898.5 1.0) (281.333333 898.500003 0.0)))
  (ar:poly "ARKA_PANE" T (list (279.333333 28.5 0.0) (531.666667 28.5 0.0) (531.666667 898.5 1.0) (279.333333 898.500003 0.0)))
  (ar:poly "ARKA_FRONT_HINGES_3MM" T (list (271.333333 20.5 0.0) (539.666667 20.5 0.0) (539.666667 898.499988 1.0) (271.333333 898.500003 0.0)))
  (ar:poly "ARKA_OUTLINE" T (list (551.666667 30.5 0.0) (664.833333 30.5 0.0) (664.833333 887.5 0.0) (551.666667 887.5 0.0)))
  (ar:poly "ARKA_PANE" T (list (549.666667 28.5 0.0) (666.833333 28.5 0.0) (666.833333 889.5 0.0) (549.666667 889.5 0.0)))
  (ar:poly "ARKA_FRONT_HINGES_3MM" T (list (541.666667 20.5 0.0) (674.833333 20.5 0.0) (674.833333 897.5 0.0) (541.666667 897.5 0.0)))
  (ar:poly "ARKA_OUTLINE" T (list (686.833333 30.5 0.0) (780.5 30.5 0.0) (780.5 887.5 0.0) (686.833333 887.5 0.0)))
  (ar:poly "ARKA_PANE" T (list (684.833333 28.5 0.0) (782.5 28.5 0.0) (782.5 889.5 0.0) (684.833333 889.5 0.0)))
  (ar:poly "ARKA_FRONT_HINGES_3MM" T (list (676.833333 20.5 0.0) (790.5 20.5 0.0) (790.5 897.5 0.0) (676.833333 897.5 0.0)))
  (ar:poly "ARKA_OUTLINE" T (list (780.338632 909.5 0.183706) (678.329113 1155.772764 0.0) (612.058763 1089.502414 -0.17866) (686.618204 909.5 0.0)))
  (ar:poly "ARKA_PANE" T (list (782.392558 907.5 0.186531) (678.367244 1158.639322 0.0) (609.279907 1089.551985 -0.182214) (684.688308 907.5 0.0)))
  (ar:poly "ARKA_FRONT_HINGES_3MM" T (list (790.498701 899.5 0.197563) (678.442299 1170.028086 0.0) (598.067444 1089.65323 -0.196997) (676.831491 899.5 0.0)))
  (ar:poly "ARKA_OUTLINE" T (list (662.772764 1171.329113 0.183706) (416.5 1273.338632 0.0) (416.5 1179.618204 -0.17866) (596.502414 1105.058763 0.0)))
  (ar:poly "ARKA_PANE" T (list (665.639322 1171.367244 0.186531) (414.5 1275.392558 0.0) (414.5 1177.688308 -0.182214) (596.551985 1102.279907 0.0)))
  (ar:poly "ARKA_FRONT_HINGES_3MM" T (list (677.028086 1171.442299 0.197563) (406.5 1283.498701 0.0) (406.5 1169.831491 -0.196997) (596.65323 1091.067444 0.0)))
  (ar:poly "ARKA_OUTLINE" T (list (394.5 1273.338632 0.183706) (148.227236 1171.329113 0.0) (214.497586 1105.058763 -0.17866) (394.5 1179.618204 0.0)))
  (ar:poly "ARKA_PANE" T (list (396.5 1275.392558 0.186531) (145.360678 1171.367244 0.0) (214.448015 1102.279907 -0.182214) (396.5 1177.688308 0.0)))
  (ar:poly "ARKA_FRONT_HINGES_3MM" T (list (404.5 1283.498701 0.197563) (133.971914 1171.442299 0.0) (214.34677 1091.067444 -0.196997) (404.5 1169.831491 0.0)))
  (ar:poly "ARKA_OUTLINE" T (list (132.670887 1155.772764 0.183706) (30.661368 909.5 0.0) (124.381796 909.5 -0.17866) (198.941237 1089.502414 0.0)))
  (ar:poly "ARKA_PANE" T (list (132.632756 1158.639322 0.186531) (28.607442 907.5 0.0) (126.311692 907.5 -0.182214) (201.720093 1089.551985 0.0)))
  (ar:poly "ARKA_FRONT_HINGES_3MM" T (list (132.557701 1170.028086 0.197563) (20.501299 899.5 0.0) (134.168509 899.5 -0.196997) (212.932556 1089.65323 0.0)))
  (ar:poly "ARKA_OUTLINE" T (list (516.340521 993.784172 -0.160031) (551.252168 909.5 0.0) (664.599938 909.5 0.176948) (596.489498 1073.933148 0.0)))
  (ar:poly "ARKA_PANE" T (list (513.606351 993.878429 -0.166632) (549.385468 907.5 0.0) (666.678313 907.5 0.181068) (596.544917 1076.816995 0.0)))
  (ar:poly "ARKA_FRONT_HINGES_3MM" T (list (502.488884 994.07467 -0.195098) (541.662995 899.5 0.0) (674.831477 899.5 0.196983) (596.65322 1088.239007 0.0)))
  (ar:poly "ARKA_OUTLINE" T (list (416.5 1044.252168 -0.160031) (500.784172 1009.340521 0.0) (580.933148 1089.489498 0.176948) (416.5 1157.599938 0.0)))
  (ar:poly "ARKA_PANE" T (list (414.5 1042.385468 -0.166632) (500.878429 1006.606351 0.0) (583.816995 1089.544917 0.181068) (414.5 1159.678313 0.0)))
  (ar:poly "ARKA_FRONT_HINGES_3MM" T (list (406.5 1034.662995 -0.195098) (501.07467 995.488884 0.0) (595.239007 1089.65322 0.196983) (406.5 1167.831477 0.0)))
  (ar:poly "ARKA_OUTLINE" T (list (310.215828 1009.340521 -0.160031) (394.5 1044.252168 0.0) (394.5 1157.599938 0.176948) (230.066852 1089.489498 0.0)))
  (ar:poly "ARKA_PANE" T (list (310.121571 1006.606351 -0.166632) (396.5 1042.385468 0.0) (396.5 1159.678313 0.181068) (227.183005 1089.544917 0.0)))
  (ar:poly "ARKA_FRONT_HINGES_3MM" T (list (309.92533 995.488884 -0.195098) (404.5 1034.662995 0.0) (404.5 1167.831477 0.196983) (215.760993 1089.65322 0.0)))
  (ar:poly "ARKA_OUTLINE" T (list (259.747832 909.5 -0.160031) (294.659479 993.784172 0.0) (214.510502 1073.933148 0.176948) (146.400062 909.5 0.0)))
  (ar:poly "ARKA_PANE" T (list (261.614532 907.5 -0.166632) (297.393649 993.878429 0.0) (214.455083 1076.816995 0.181068) (144.321687 907.5 0.0)))
  (ar:poly "ARKA_FRONT_HINGES_3MM" T (list (269.337005 899.5 -0.195098) (308.511116 994.07467 0.0) (214.34678 1088.239007 0.196983) (136.168523 899.5 0.0)))
  (ar:poly "ARKA_MITRE" nil (list (20.5 35.5 0.0) (20.5 20.5 0.0) (35.5 20.5 0.0)))
  (ar:poly "ARKA_MITRE" nil (list (119.166667 20.5 0.0) (134.166667 20.5 0.0) (134.166667 35.5 0.0)))
  (ar:poly "ARKA_MITRE" nil (list (134.166667 882.5 0.0) (134.166667 897.5 0.0) (119.166667 897.5 0.0)))
  (ar:poly "ARKA_MITRE" nil (list (35.5 897.5 0.0) (20.5 897.5 0.0) (20.5 882.5 0.0)))
  (ar:poly "ARKA_MITRE" nil (list (136.166667 35.5 0.0) (136.166667 20.5 0.0) (151.166667 20.5 0.0)))
  (ar:poly "ARKA_MITRE" nil (list (254.333333 20.5 0.0) (269.333333 20.5 0.0) (269.333333 35.5 0.0)))
  (ar:poly "ARKA_MITRE" nil (list (269.333333 882.5 0.0) (269.333333 897.5 0.0) (254.333333 897.5 0.0)))
  (ar:poly "ARKA_MITRE" nil (list (151.166667 897.5 0.0) (136.166667 897.5 0.0) (136.166667 882.5 0.0)))
  (ar:poly "ARKA_MITRE" nil (list (271.333333 35.5 0.0) (271.333333 20.5 0.0) (286.333333 20.5 0.0)))
  (ar:poly "ARKA_MITRE" nil (list (524.666667 20.5 0.0) (539.666667 20.5 0.0) (539.666667 35.5 0.0)))
  (ar:poly "ARKA_MITRE" nil (list (541.666667 35.5 0.0) (541.666667 20.5 0.0) (556.666667 20.5 0.0)))
  (ar:poly "ARKA_MITRE" nil (list (659.833333 20.5 0.0) (674.833333 20.5 0.0) (674.833333 35.5 0.0)))
  (ar:poly "ARKA_MITRE" nil (list (674.833333 882.5 0.0) (674.833333 897.5 0.0) (659.833333 897.5 0.0)))
  (ar:poly "ARKA_MITRE" nil (list (556.666667 897.5 0.0) (541.666667 897.5 0.0) (541.666667 882.5 0.0)))
  (ar:poly "ARKA_MITRE" nil (list (676.833333 35.5 0.0) (676.833333 20.5 0.0) (691.833333 20.5 0.0)))
  (ar:poly "ARKA_MITRE" nil (list (775.5 20.5 0.0) (790.5 20.5 0.0) (790.5 35.5 0.0)))
  (ar:poly "ARKA_MITRE" nil (list (790.5 882.5 0.0) (790.5 897.5 0.0) (775.5 897.5 0.0)))
  (ar:poly "ARKA_MITRE" nil (list (691.833333 897.5 0.0) (676.833333 897.5 0.0) (676.833333 882.5 0.0)))
  (ar:poly "ARKA_MITRE" nil (list (775.498701 899.5 0.0) (790.498701 899.5 0.009741) (790.16758 914.495396 0.0)))
  (ar:poly "ARKA_MITRE" nil (list (688.811507 1159.190602 0.009741) (678.442299 1170.028086 0.0) (667.835697 1159.421484 0.0)))
  (ar:poly "ARKA_MITRE" nil (list (608.674045 1100.259832 0.0) (598.067444 1089.65323 -0.013822) (608.335317 1078.721008 0.0)))
  (ar:poly "ARKA_MITRE" nil (list (676.361725 914.490731 -0.013822) (676.831491 899.5 0.0) (691.831491 899.5 0.0)))
  (ar:poly "ARKA_MITRE" nil (list (666.421484 1160.835697 0.0) (677.028086 1171.442299 0.009741) (666.190602 1181.811507 0.0)))
  (ar:poly "ARKA_MITRE" nil (list (421.495396 1283.16758 0.009741) (406.5 1283.498701 0.0) (406.5 1268.498701 0.0)))
  (ar:poly "ARKA_MITRE" nil (list (406.5 1184.831491 0.0) (406.5 1169.831491 -0.013822) (421.490731 1169.361725 0.0)))
  (ar:poly "ARKA_MITRE" nil (list (585.721008 1101.335317 -0.013822) (596.65323 1091.067444 0.0) (607.259832 1101.674045 0.0)))
  (ar:poly "ARKA_MITRE" nil (list (404.5 1268.498701 0.0) (404.5 1283.498701 0.009741) (389.504604 1283.16758 0.0)))
  (ar:poly "ARKA_MITRE" nil (list (144.809398 1181.811507 0.009741) (133.971914 1171.442299 0.0) (144.578516 1160.835697 0.0)))
  (ar:poly "ARKA_MITRE" nil (list (203.740168 1101.674045 0.0) (214.34677 1091.067444 -0.013822) (225.278992 1101.335317 0.0)))
  (ar:poly "ARKA_MITRE" nil (list (389.509269 1169.361725 -0.013822) (404.5 1169.831491 0.0) (404.5 1184.831491 0.0)))
  (ar:poly "ARKA_MITRE" nil (list (143.164303 1159.421484 0.0) (132.557701 1170.028086 0.009741) (122.188493 1159.190602 0.0)))
  (ar:poly "ARKA_MITRE" nil (list (20.83242 914.495396 0.009741) (20.501299 899.5 0.0) (35.501299 899.5 0.0)))
  (ar:poly "ARKA_MITRE" nil (list (119.168509 899.5 0.0) (134.168509 899.5 -0.013822) (134.638275 914.490731 0.0)))
  (ar:poly "ARKA_MITRE" nil (list (202.664683 1078.721008 -0.013822) (212.932556 1089.65323 0.0) (202.325955 1100.259832 0.0)))
  (ar:poly "ARKA_MITRE" nil (list (513.095485 1004.681272 0.0) (502.488884 994.07467 -0.027547) (512.408137 982.832741 0.0)))
  (ar:poly "ARKA_MITRE" nil (list (540.727722 914.463216 -0.027547) (541.662995 899.5 0.0) (556.662995 899.5 0.0)))
  (ar:poly "ARKA_MITRE" nil (list (659.831477 899.5 0.0) (674.831477 899.5 0.013924) (674.358225 914.490593 0.0)))
  (ar:poly "ARKA_MITRE" nil (list (606.918531 1077.304418 0.013924) (596.65322 1088.239007 0.0) (586.046619 1077.632405 0.0)))
  (ar:poly "ARKA_MITRE" nil (list (406.5 1049.662995 0.0) (406.5 1034.662995 -0.027547) (421.463216 1033.727722 0.0)))
  (ar:poly "ARKA_MITRE" nil (list (489.832741 1005.408137 -0.027547) (501.07467 995.488884 0.0) (511.681272 1006.095485 0.0)))
  (ar:poly "ARKA_MITRE" nil (list (584.632405 1079.046619 0.0) (595.239007 1089.65322 0.013924) (584.304418 1099.918531 0.0)))
  (ar:poly "ARKA_MITRE" nil (list (421.490593 1167.358225 0.013924) (406.5 1167.831477 0.0) (406.5 1152.831477 0.0)))
  (ar:poly "ARKA_MITRE" nil (list (299.318728 1006.095485 0.0) (309.92533 995.488884 -0.027547) (321.167259 1005.408137 0.0)))
  (ar:poly "ARKA_MITRE" nil (list (389.536784 1033.727722 -0.027547) (404.5 1034.662995 0.0) (404.5 1049.662995 0.0)))
  (ar:poly "ARKA_MITRE" nil (list (404.5 1152.831477 0.0) (404.5 1167.831477 0.013924) (389.509407 1167.358225 0.0)))
  (ar:poly "ARKA_MITRE" nil (list (226.695582 1099.918531 0.013924) (215.760993 1089.65322 0.0) (226.367595 1079.046619 0.0)))
  (ar:poly "ARKA_MITRE" nil (list (254.337005 899.5 0.0) (269.337005 899.5 -0.027547) (270.272278 914.463216 0.0)))
  (ar:poly "ARKA_MITRE" nil (list (298.591863 982.832741 -0.027547) (308.511116 994.07467 0.0) (297.904515 1004.681272 0.0)))
  (ar:poly "ARKA_MITRE" nil (list (224.953381 1077.632405 0.0) (214.34678 1088.239007 0.013924) (204.081469 1077.304418 0.0)))
  (ar:poly "ARKA_MITRE" nil (list (136.641775 914.490593 0.013924) (136.168523 899.5 0.0) (151.168523 899.5 0.0)))
  (ar:point "ARKA_CENTRE" 405.5 898.5)
  (ar:poly "ARKA_SECTION" nil (list (898.5 12.5 -0.414214) (906.5 20.5 0.0) (906.5 26.5 0.0)))
  (ar:text "ARKA_INFO_NO_CUT" 894.5 -6.5 15.0 "START")
  (ar:text "ARKA_INFO_NO_CUT" 918.5 16.5 15.0 "SECTION R8 + 6 (VERBATIM)")
  (ar:text "ARKA_INFO_NO_CUT" 898.5 1269.5 15.0 "quad - TRACERY FULL")
  (ar:text "ARKA_INFO_NO_CUT" 898.5 1247.5 15.0 "PATTERN QUAD-HUB-SPOKE SPOKES 11 RINGS 2 PANES 13")
  (ar:text "ARKA_INFO_NO_CUT" 898.5 1225.5 15.0 "TIMBER BAR 22 EDGE MARGIN 18 PANE +2 LIMIT +10 MITRE LEG 15")
  (ar:text "ARKA_INFO_NO_CUT" 898.5 1203.5 15.0 "ARKA_PANE = MOULDING RAIL (INNER EDGE OF THE BEAD), ARKA_FRONT_HINGES_3MM = BEAD LIMIT (NOT DRILLING)")
  (ar:text "ARKA_INFO_NO_CUT" 898.5 1181.5 15.0 "NOT A TOOLPATH")
  (princ "\nARKA: tracery drawn. Layers ARKA_*; ARKA_INFO_NO_CUT is not a toolpath.")
  (princ)
)
(princ "\nARKA loaded - type ARKA to draw the tracery.")
(princ)
