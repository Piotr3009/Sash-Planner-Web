;;; ARKA tracery — generated by Production Core (ARCHED-WINDOWS-v3 Block 0.4)
;;; window custom - pattern custom - units mm - layers ARKA_*
;;; The DXF of the same name carries the same entities; ARKA_INFO_NO_CUT is never machined.
(defun ar:layer (name col)
  (if (not (tblsearch "LAYER" name))
    (command "_.-LAYER" "_M" name "_C" (itoa col) name "")
    (command "_.-LAYER" "_S" name ""))
)
(defun ar:poly (layer closed verts / data v)
  (setq data (list (quote (0 . "LWPOLYLINE")) (quote (100 . "AcDbEntity")) (cons 8 layer)
                   (quote (100 . "AcDbPolyline")) (cons 90 (length verts)) (cons 70 (if closed 1 0))))
  (foreach v verts
    (setq data (append data (list (cons 10 (list (+ (car *ar-ip*) (car v)) (+ (cadr *ar-ip*) (cadr v)))) (cons 42 (caddr v))))))
  (entmake data)
)
(defun ar:point (layer x y)
  (entmake (list (quote (0 . "POINT")) (cons 8 layer) (cons 10 (list (+ (car *ar-ip*) x) (+ (cadr *ar-ip*) y) 0.0))))
)
(defun ar:text (layer x y h str)
  (entmake (list (quote (0 . "TEXT")) (cons 8 layer) (cons 10 (list (+ (car *ar-ip*) x) (+ (cadr *ar-ip*) y) 0.0)) (cons 40 h) (cons 1 str)))
)
(defun c:ARKA ( / ip)
  (setq ip (getpoint "\nInsertion point <0,0>: "))
  (setq *ar-ip* (if ip (list (car ip) (cadr ip)) (list 0.0 0.0)))
  (ar:layer "ARKA_OUTLINE" 7)
  (ar:layer "ARKA_PANE" 3)
  (ar:layer "ARKA_FRONT_HINGES_3MM" 50)
  (ar:layer "ARKA_MITRE" 1)
  (ar:layer "ARKA_SECTION" 5)
  (ar:layer "ARKA_PANE_ZEWN_REF" 3)
  (ar:layer "ARKA_CENTRE" 6)
  (ar:layer "ARKA_INFO_NO_CUT" 8)
  (ar:poly "ARKA_OUTLINE" T (list (12.5 12.5 0.0) (998.5 12.5 0.0) (998.5 1098.5 1.0) (12.5 1098.5 0.0)))
  (ar:poly "ARKA_PANE_ZEWN_REF" T (list (14.5 14.5 0.0) (996.5 14.5 0.0) (996.5 1098.5 1.0) (14.5 1098.5 0.0)))
  (ar:poly "ARKA_OUTLINE" T (list (30.5 30.5 0.0) (216.475 30.5 0.0) (216.475 1087.5 0.0) (30.5 1087.5 0.0)))
  (ar:poly "ARKA_PANE" T (list (28.5 28.5 0.0) (218.475 28.5 0.0) (218.475 1089.5 0.0) (28.5 1089.5 0.0)))
  (ar:poly "ARKA_FRONT_HINGES_3MM" T (list (20.5 20.5 0.0) (226.475 20.5 0.0) (226.475 1097.5 0.0) (20.5 1097.5 0.0)))
  (ar:poly "ARKA_OUTLINE" T (list (238.475 30.5 0.0) (368.125 30.5 0.0) (368.125 1087.5 0.0) (238.475 1087.5 0.0)))
  (ar:poly "ARKA_PANE" T (list (236.475 28.5 0.0) (370.125 28.5 0.0) (370.125 1089.5 0.0) (236.475 1089.5 0.0)))
  (ar:poly "ARKA_FRONT_HINGES_3MM" T (list (228.475 20.5 0.0) (378.125 20.5 0.0) (378.125 1097.5 0.0) (228.475 1097.5 0.0)))
  (ar:poly "ARKA_OUTLINE" T (list (390.125 30.5 0.0) (620.875 30.5 0.0) (620.875 1098.5 1.0) (390.125 1098.5 0.0)))
  (ar:poly "ARKA_PANE" T (list (388.125 28.5 0.0) (622.875 28.5 0.0) (622.875 1098.5 1.0) (388.125 1098.5 0.0)))
  (ar:poly "ARKA_FRONT_HINGES_3MM" T (list (380.125 20.5 0.0) (630.875 20.5 0.0) (630.875 1098.5 1.0) (380.125 1098.5 0.0)))
  (ar:poly "ARKA_OUTLINE" T (list (642.875 30.5 0.0) (772.525 30.5 0.0) (772.525 1087.5 0.0) (642.875 1087.5 0.0)))
  (ar:poly "ARKA_PANE" T (list (640.875 28.5 0.0) (774.525 28.5 0.0) (774.525 1089.5 0.0) (640.875 1089.5 0.0)))
  (ar:poly "ARKA_FRONT_HINGES_3MM" T (list (632.875 20.5 0.0) (782.525 20.5 0.0) (782.525 1097.5 0.0) (632.875 1097.5 0.0)))
  (ar:poly "ARKA_OUTLINE" T (list (794.525 30.5 0.0) (980.5 30.5 0.0) (980.5 1087.5 0.0) (794.525 1087.5 0.0)))
  (ar:poly "ARKA_PANE" T (list (792.525 28.5 0.0) (982.5 28.5 0.0) (982.5 1089.5 0.0) (792.525 1089.5 0.0)))
  (ar:poly "ARKA_FRONT_HINGES_3MM" T (list (784.525 20.5 0.0) (990.5 20.5 0.0) (990.5 1097.5 0.0) (784.525 1097.5 0.0)))
  (ar:poly "ARKA_OUTLINE" T (list (980.372614 1109.5 0.119889) (922.251748 1326.410028 0.0) (761.121646 1233.38152 -0.112335) (794.3156 1109.5 0.0)))
  (ar:poly "ARKA_PANE" T (list (982.415087 1107.5 0.122066) (923.020581 1329.163315 0.0) (758.448713 1234.147703 -0.115732) (792.383863 1107.5 0.0)))
  (ar:poly "ARKA_FRONT_HINGES_3MM" T (list (990.498969 1099.5 0.130604) (926.021428 1340.133459 0.0) (747.641186 1237.145579 -0.12983) (784.523208 1099.5 0.0)))
  (ar:poly "ARKA_OUTLINE" T (list (911.251748 1345.462587 0.119889) (752.462587 1504.251748 0.0) (659.434079 1343.121646 -0.112335) (750.121646 1252.434079 0.0)))
  (ar:poly "ARKA_PANE" T (list (914.020581 1344.751772 0.122066) (751.751772 1507.020581 0.0) (656.73616 1342.448713 -0.115732) (749.448713 1249.73616 0.0)))
  (ar:poly "ARKA_FRONT_HINGES_3MM" T (list (925.021428 1341.86551 0.130604) (748.86551 1518.021428 0.0) (645.877629 1339.641186 -0.12983) (746.641186 1238.877629 0.0)))
  (ar:poly "ARKA_OUTLINE" T (list (733.410028 1515.251748 0.119889) (516.5 1573.372614 0.0) (516.5 1387.3156 -0.112335) (640.38152 1354.121646 0.0)))
  (ar:poly "ARKA_PANE" T (list (736.163315 1516.020581 0.122066) (514.5 1575.415087 0.0) (514.5 1385.383863 -0.115732) (641.147703 1351.448713 0.0)))
  (ar:poly "ARKA_FRONT_HINGES_3MM" T (list (747.133459 1519.021428 0.130604) (506.5 1583.498969 0.0) (506.5 1377.523208 -0.12983) (644.145579 1340.641186 0.0)))
  (ar:poly "ARKA_OUTLINE" T (list (494.5 1573.372614 0.119889) (277.589972 1515.251748 0.0) (370.61848 1354.121646 -0.112335) (494.5 1387.3156 0.0)))
  (ar:poly "ARKA_PANE" T (list (496.5 1575.415087 0.122066) (274.836685 1516.020581 0.0) (369.852297 1351.448713 -0.115732) (496.5 1385.383863 0.0)))
  (ar:poly "ARKA_FRONT_HINGES_3MM" T (list (504.5 1583.498969 0.130604) (263.866541 1519.021428 0.0) (366.854421 1340.641186 -0.12983) (504.5 1377.523208 0.0)))
  (ar:poly "ARKA_OUTLINE" T (list (258.537413 1504.251748 0.119889) (99.748252 1345.462587 0.0) (260.878354 1252.434079 -0.112335) (351.565921 1343.121646 0.0)))
  (ar:poly "ARKA_PANE" T (list (259.248228 1507.020581 0.122066) (96.979419 1344.751772 0.0) (261.551287 1249.73616 -0.115732) (354.26384 1342.448713 0.0)))
  (ar:poly "ARKA_FRONT_HINGES_3MM" T (list (262.13449 1518.021428 0.130604) (85.978572 1341.86551 0.0) (264.358814 1238.877629 -0.12983) (365.122371 1339.641186 0.0)))
  (ar:poly "ARKA_OUTLINE" T (list (88.748252 1326.410028 0.119889) (30.627386 1109.5 0.0) (216.6844 1109.5 -0.112335) (249.878354 1233.38152 0.0)))
  (ar:poly "ARKA_PANE" T (list (87.979419 1329.163315 0.122066) (28.584913 1107.5 0.0) (218.616137 1107.5 -0.115732) (252.551287 1234.147703 0.0)))
  (ar:poly "ARKA_FRONT_HINGES_3MM" T (list (84.978572 1340.133459 0.130604) (20.501031 1099.5 0.0) (226.476792 1099.5 -0.12983) (263.358814 1237.145579 0.0)))
  (ar:poly "ARKA_OUTLINE" T (list (629.588229 1157.440666 -0.091071) (642.433891 1109.5 0.0) (772.298333 1109.5 0.110746) (742.054134 1222.372887 0.0)))
  (ar:poly "ARKA_PANE" T (list (626.978814 1158.243521 -0.097946) (640.5755 1107.5 0.0) (774.374414 1107.5 0.114668) (742.852073 1225.142978 0.0)))
  (ar:poly "ARKA_FRONT_HINGES_3MM" T (list (616.306586 1161.319512 -0.127661) (632.871075 1099.5 0.0) (782.523195 1099.5 0.129817) (745.909124 1236.145572 0.0)))
  (ar:poly "ARKA_OUTLINE" T (list (583.493225 1211.588229 -0.091071) (618.588229 1176.493225 0.0) (731.054134 1241.425446 0.110746) (648.425446 1324.054134 0.0)))
  (ar:poly "ARKA_PANE" T (list (580.831978 1210.978814 -0.097946) (617.978814 1173.831978 0.0) (733.852073 1240.731436 0.114668) (647.731436 1326.852073 0.0)))
  (ar:poly "ARKA_FRONT_HINGES_3MM" T (list (570.051563 1208.306586 -0.127661) (615.306586 1163.051563 0.0) (744.909124 1237.877623 0.129817) (644.877623 1337.909124 0.0)))
  (ar:poly "ARKA_OUTLINE" T (list (516.5 1235.433891 -0.091071) (564.440666 1222.588229 0.0) (629.372887 1335.054134 0.110746) (516.5 1365.298333 0.0)))
  (ar:poly "ARKA_PANE" T (list (514.5 1233.5755 -0.097946) (565.243521 1219.978814 0.0) (632.142978 1335.852073 0.114668) (514.5 1367.374414 0.0)))
  (ar:poly "ARKA_FRONT_HINGES_3MM" T (list (506.5 1225.871075 -0.127661) (568.319512 1209.306586 0.0) (643.145572 1338.909124 0.129817) (506.5 1375.523195 0.0)))
  (ar:poly "ARKA_OUTLINE" T (list (446.559334 1222.588229 -0.091071) (494.5 1235.433891 0.0) (494.5 1365.298333 0.110746) (381.627113 1335.054134 0.0)))
  (ar:poly "ARKA_PANE" T (list (445.756479 1219.978814 -0.097946) (496.5 1233.5755 0.0) (496.5 1367.374414 0.114668) (378.857022 1335.852073 0.0)))
  (ar:poly "ARKA_FRONT_HINGES_3MM" T (list (442.680488 1209.306586 -0.127661) (504.5 1225.871075 0.0) (504.5 1375.523195 0.129817) (367.854428 1338.909124 0.0)))
  (ar:poly "ARKA_OUTLINE" T (list (392.411771 1176.493225 -0.091071) (427.506775 1211.588229 0.0) (362.574554 1324.054134 0.110746) (279.945866 1241.425446 0.0)))
  (ar:poly "ARKA_PANE" T (list (393.021186 1173.831978 -0.097946) (430.168022 1210.978814 0.0) (363.268564 1326.852073 0.114668) (277.147927 1240.731436 0.0)))
  (ar:poly "ARKA_FRONT_HINGES_3MM" T (list (395.693414 1163.051563 -0.127661) (440.948437 1208.306586 0.0) (366.122377 1337.909124 0.129817) (266.090876 1237.877623 0.0)))
  (ar:poly "ARKA_OUTLINE" T (list (368.566109 1109.5 -0.091071) (381.411771 1157.440666 0.0) (268.945866 1222.372887 0.110746) (238.701667 1109.5 0.0)))
  (ar:poly "ARKA_PANE" T (list (370.4245 1107.5 -0.097946) (384.021186 1158.243521 0.0) (268.147927 1225.142978 0.114668) (236.625586 1107.5 0.0)))
  (ar:poly "ARKA_FRONT_HINGES_3MM" T (list (378.128925 1099.5 -0.127661) (394.693414 1161.319512 0.0) (265.090876 1236.145572 0.129817) (228.476805 1099.5 0.0)))
  (ar:poly "ARKA_MITRE" nil (list (20.5 35.5 0.0) (20.5 20.5 0.0) (35.5 20.5 0.0)))
  (ar:poly "ARKA_MITRE" nil (list (211.475 20.5 0.0) (226.475 20.5 0.0) (226.475 35.5 0.0)))
  (ar:poly "ARKA_MITRE" nil (list (226.475 1082.5 0.0) (226.475 1097.5 0.0) (211.475 1097.5 0.0)))
  (ar:poly "ARKA_MITRE" nil (list (35.5 1097.5 0.0) (20.5 1097.5 0.0) (20.5 1082.5 0.0)))
  (ar:poly "ARKA_MITRE" nil (list (228.475 35.5 0.0) (228.475 20.5 0.0) (243.475 20.5 0.0)))
  (ar:poly "ARKA_MITRE" nil (list (363.125 20.5 0.0) (378.125 20.5 0.0) (378.125 35.5 0.0)))
  (ar:poly "ARKA_MITRE" nil (list (378.125 1082.5 0.0) (378.125 1097.5 0.0) (363.125 1097.5 0.0)))
  (ar:poly "ARKA_MITRE" nil (list (243.475 1097.5 0.0) (228.475 1097.5 0.0) (228.475 1082.5 0.0)))
  (ar:poly "ARKA_MITRE" nil (list (380.125 35.5 0.0) (380.125 20.5 0.0) (395.125 20.5 0.0)))
  (ar:poly "ARKA_MITRE" nil (list (615.875 20.5 0.0) (630.875 20.5 0.0) (630.875 35.5 0.0)))
  (ar:poly "ARKA_MITRE" nil (list (632.875 35.5 0.0) (632.875 20.5 0.0) (647.875 20.5 0.0)))
  (ar:poly "ARKA_MITRE" nil (list (767.525 20.5 0.0) (782.525 20.5 0.0) (782.525 35.5 0.0)))
  (ar:poly "ARKA_MITRE" nil (list (782.525 1082.5 0.0) (782.525 1097.5 0.0) (767.525 1097.5 0.0)))
  (ar:poly "ARKA_MITRE" nil (list (647.875 1097.5 0.0) (632.875 1097.5 0.0) (632.875 1082.5 0.0)))
  (ar:poly "ARKA_MITRE" nil (list (784.525 35.5 0.0) (784.525 20.5 0.0) (799.525 20.5 0.0)))
  (ar:poly "ARKA_MITRE" nil (list (975.5 20.5 0.0) (990.5 20.5 0.0) (990.5 35.5 0.0)))
  (ar:poly "ARKA_MITRE" nil (list (990.5 1082.5 0.0) (990.5 1097.5 0.0) (975.5 1097.5 0.0)))
  (ar:poly "ARKA_MITRE" nil (list (799.525 1097.5 0.0) (784.525 1097.5 0.0) (784.525 1082.5 0.0)))
  (ar:poly "ARKA_MITRE" nil (list (975.498969 1099.5 0.0) (990.498969 1099.5 0.007732) (990.236106 1114.497099 0.0)))
  (ar:poly "ARKA_MITRE" nil (list (933.292332 1327.014159 0.007732) (926.021428 1340.133459 0.0) (913.031047 1332.633459 0.0)))
  (ar:poly "ARKA_MITRE" nil (list (760.631567 1244.645579 0.0) (747.641186 1237.145579 -0.01344) (754.741184 1223.934377 0.0)))
  (ar:poly "ARKA_MITRE" nil (list (784.066385 1114.491235 -0.01344) (784.523208 1099.5 0.0) (799.523208 1099.5 0.0)))
  (ar:poly "ARKA_MITRE" nil (list (912.031047 1334.36551 0.0) (925.021428 1341.86551 0.007732) (917.295233 1354.721947 0.0)))
  (ar:poly "ARKA_MITRE" nil (list (761.721947 1510.295233 0.007732) (748.86551 1518.021428 0.0) (741.36551 1505.031047 0.0)))
  (ar:poly "ARKA_MITRE" nil (list (653.377629 1352.631567 0.0) (645.877629 1339.641186 -0.01344) (658.632009 1331.749949 0.0)))
  (ar:poly "ARKA_MITRE" nil (list (738.749949 1251.632009 -0.01344) (746.641186 1238.877629 0.0) (759.631567 1246.377629 0.0)))
  (ar:poly "ARKA_MITRE" nil (list (739.633459 1506.031047 0.0) (747.133459 1519.021428 0.007732) (734.014159 1526.292332 0.0)))
  (ar:poly "ARKA_MITRE" nil (list (521.497099 1583.236106 0.007732) (506.5 1583.498969 0.0) (506.5 1568.498969 0.0)))
  (ar:poly "ARKA_MITRE" nil (list (506.5 1392.523208 0.0) (506.5 1377.523208 -0.01344) (521.491235 1377.066385 0.0)))
  (ar:poly "ARKA_MITRE" nil (list (630.934377 1347.741184 -0.01344) (644.145579 1340.641186 0.0) (651.645579 1353.631567 0.0)))
  (ar:poly "ARKA_MITRE" nil (list (504.5 1568.498969 0.0) (504.5 1583.498969 0.007732) (489.502901 1583.236106 0.0)))
  (ar:poly "ARKA_MITRE" nil (list (276.985841 1526.292332 0.007732) (263.866541 1519.021428 0.0) (271.366541 1506.031047 0.0)))
  (ar:poly "ARKA_MITRE" nil (list (359.354421 1353.631567 0.0) (366.854421 1340.641186 -0.01344) (380.065623 1347.741184 0.0)))
  (ar:poly "ARKA_MITRE" nil (list (489.508765 1377.066385 -0.01344) (504.5 1377.523208 0.0) (504.5 1392.523208 0.0)))
  (ar:poly "ARKA_MITRE" nil (list (269.63449 1505.031047 0.0) (262.13449 1518.021428 0.007732) (249.278053 1510.295233 0.0)))
  (ar:poly "ARKA_MITRE" nil (list (93.704767 1354.721947 0.007732) (85.978572 1341.86551 0.0) (98.968953 1334.36551 0.0)))
  (ar:poly "ARKA_MITRE" nil (list (251.368433 1246.377629 0.0) (264.358814 1238.877629 -0.01344) (272.250051 1251.632009 0.0)))
  (ar:poly "ARKA_MITRE" nil (list (352.367991 1331.749949 -0.01344) (365.122371 1339.641186 0.0) (357.622371 1352.631567 0.0)))
  (ar:poly "ARKA_MITRE" nil (list (97.968953 1332.633459 0.0) (84.978572 1340.133459 0.007732) (77.707668 1327.014159 0.0)))
  (ar:poly "ARKA_MITRE" nil (list (20.763894 1114.497099 0.007732) (20.501031 1099.5 0.0) (35.501031 1099.5 0.0)))
  (ar:poly "ARKA_MITRE" nil (list (211.476792 1099.5 0.0) (226.476792 1099.5 -0.01344) (226.933615 1114.491235 0.0)))
  (ar:poly "ARKA_MITRE" nil (list (256.258816 1223.934377 -0.01344) (263.358814 1237.145579 0.0) (250.368433 1244.645579 0.0)))
  (ar:poly "ARKA_MITRE" nil (list (629.296967 1168.819512 0.0) (616.306586 1161.319512 -0.029449) (622.919837 1147.865702 0.0)))
  (ar:poly "ARKA_MITRE" nil (list (631.871413 1114.457967 -0.029449) (632.871075 1099.5 0.0) (647.871075 1099.5 0.0)))
  (ar:poly "ARKA_MITRE" nil (list (767.523195 1099.5 0.0) (782.523195 1099.5 0.013538) (782.063076 1114.491108 0.0)))
  (ar:poly "ARKA_MITRE" nil (list (753.006204 1222.932832 0.013538) (745.909124 1236.145572 0.0) (732.918743 1228.645572 0.0)))
  (ar:poly "ARKA_MITRE" nil (list (577.551563 1221.296967 0.0) (570.051563 1208.306586 -0.029449) (582.505711 1199.96187 0.0)))
  (ar:poly "ARKA_MITRE" nil (list (606.96187 1175.505711 -0.029449) (615.306586 1163.051563 0.0) (628.296967 1170.551563 0.0)))
  (ar:poly "ARKA_MITRE" nil (list (731.918743 1230.377623 0.0) (744.909124 1237.877623 0.013538) (737.015096 1250.630244 0.0)))
  (ar:poly "ARKA_MITRE" nil (list (657.630244 1330.015096 0.013538) (644.877623 1337.909124 0.0) (637.377623 1324.918743 0.0)))
  (ar:poly "ARKA_MITRE" nil (list (506.5 1240.871075 0.0) (506.5 1225.871075 -0.029449) (521.457967 1224.871413 0.0)))
  (ar:poly "ARKA_MITRE" nil (list (554.865702 1215.919837 -0.029449) (568.319512 1209.306586 0.0) (575.819512 1222.296967 0.0)))
  (ar:poly "ARKA_MITRE" nil (list (635.645572 1325.918743 0.0) (643.145572 1338.909124 0.013538) (629.932832 1346.006204 0.0)))
  (ar:poly "ARKA_MITRE" nil (list (521.491108 1375.063076 0.013538) (506.5 1375.523195 0.0) (506.5 1360.523195 0.0)))
  (ar:poly "ARKA_MITRE" nil (list (435.180488 1222.296967 0.0) (442.680488 1209.306586 -0.029449) (456.134298 1215.919837 0.0)))
  (ar:poly "ARKA_MITRE" nil (list (489.542033 1224.871413 -0.029449) (504.5 1225.871075 0.0) (504.5 1240.871075 0.0)))
  (ar:poly "ARKA_MITRE" nil (list (504.5 1360.523195 0.0) (504.5 1375.523195 0.013538) (489.508892 1375.063076 0.0)))
  (ar:poly "ARKA_MITRE" nil (list (381.067168 1346.006204 0.013538) (367.854428 1338.909124 0.0) (375.354428 1325.918743 0.0)))
  (ar:poly "ARKA_MITRE" nil (list (382.703033 1170.551563 0.0) (395.693414 1163.051563 -0.029449) (404.03813 1175.505711 0.0)))
  (ar:poly "ARKA_MITRE" nil (list (428.494289 1199.96187 -0.029449) (440.948437 1208.306586 0.0) (433.448437 1221.296967 0.0)))
  (ar:poly "ARKA_MITRE" nil (list (373.622377 1324.918743 0.0) (366.122377 1337.909124 0.013538) (353.369756 1330.015096 0.0)))
  (ar:poly "ARKA_MITRE" nil (list (273.984904 1250.630244 0.013538) (266.090876 1237.877623 0.0) (279.081257 1230.377623 0.0)))
  (ar:poly "ARKA_MITRE" nil (list (363.128925 1099.5 0.0) (378.128925 1099.5 -0.029449) (379.128587 1114.457967 0.0)))
  (ar:poly "ARKA_MITRE" nil (list (388.080163 1147.865702 -0.029449) (394.693414 1161.319512 0.0) (381.703033 1168.819512 0.0)))
  (ar:poly "ARKA_MITRE" nil (list (278.081257 1228.645572 0.0) (265.090876 1236.145572 0.013538) (257.993796 1222.932832 0.0)))
  (ar:poly "ARKA_MITRE" nil (list (228.936924 1114.491108 0.013538) (228.476805 1099.5 0.0) (243.476805 1099.5 0.0)))
  (ar:point "ARKA_CENTRE" 505.5 1098.5)
  (ar:poly "ARKA_SECTION" nil (list (1098.5 12.5 -0.414214) (1106.5 20.5 0.0) (1106.5 26.5 0.0)))
  (ar:text "ARKA_INFO_NO_CUT" 1094.5 -6.5 15.0 "START")
  (ar:text "ARKA_INFO_NO_CUT" 1118.5 16.5 15.0 "SECTION R8 + 6 (VERBATIM)")
  (ar:text "ARKA_INFO_NO_CUT" 1098.5 1569.5 15.0 "custom - TRACERY FULL")
  (ar:text "ARKA_INFO_NO_CUT" 1098.5 1547.5 15.0 "PATTERN CUSTOM SPOKES 14 RINGS 2 PANES 17")
  (ar:text "ARKA_INFO_NO_CUT" 1098.5 1525.5 15.0 "TIMBER BAR 22 EDGE MARGIN 18 PANE +2 LIMIT +10 MITRE LEG 15")
  (ar:text "ARKA_INFO_NO_CUT" 1098.5 1503.5 15.0 "ARKA_PANE = MOULDING RAIL (INNER EDGE OF THE BEAD), ARKA_FRONT_HINGES_3MM = BEAD LIMIT (NOT DRILLING)")
  (ar:text "ARKA_INFO_NO_CUT" 1098.5 1481.5 15.0 "NOT A TOOLPATH")
  (princ "\nARKA: tracery drawn. Layers ARKA_*; ARKA_INFO_NO_CUT is not a toolpath.")
  (princ)
)
(princ "\nARKA loaded - type ARKA to draw the tracery.")
(princ)
