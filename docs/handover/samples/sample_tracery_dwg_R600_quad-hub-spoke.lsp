;;; ARKA tracery — generated by Production Core (ARCHED-WINDOWS-v3 Block 0.4)
;;; window DWG - pattern quad-hub-spoke - units mm - layers ARKA_*
;;; The DXF of the same name carries the same entities; ARKA_INFO_NO_CUT is never machined.
(defun ar:layer (name col)
  (if (not (tblsearch "LAYER" name))
    (command "_.-LAYER" "_M" name "_C" (itoa col) name "")
    (command "_.-LAYER" "_S" name ""))
)
(defun ar:poly (layer closed verts / data v)
  (setq data (list (quote (0 . "LWPOLYLINE")) (quote (100 . "AcDbEntity")) (cons 8 layer)
                   (quote (100 . "AcDbPolyline")) (cons 90 (length verts)) (cons 70 (if closed 1 0))))
  (foreach v verts
    (setq data (append data (list (cons 10 (list (+ (car *ar-ip*) (car v)) (+ (cadr *ar-ip*) (cadr v)))) (cons 42 (caddr v))))))
  (entmake data)
)
(defun ar:point (layer x y)
  (entmake (list (quote (0 . "POINT")) (cons 8 layer) (cons 10 (list (+ (car *ar-ip*) x) (+ (cadr *ar-ip*) y) 0.0))))
)
(defun ar:text (layer x y h str)
  (entmake (list (quote (0 . "TEXT")) (cons 8 layer) (cons 10 (list (+ (car *ar-ip*) x) (+ (cadr *ar-ip*) y) 0.0)) (cons 40 h) (cons 1 str)))
)
(defun c:ARKA ( / ip)
  (setq ip (getpoint "\nInsertion point <0,0>: "))
  (setq *ar-ip* (if ip (list (car ip) (cadr ip)) (list 0.0 0.0)))
  (ar:layer "ARKA_OUTLINE" 7)
  (ar:layer "ARKA_PANE" 3)
  (ar:layer "ARKA_FRONT_HINGES_3MM" 50)
  (ar:layer "ARKA_MITRE" 1)
  (ar:layer "ARKA_SECTION" 5)
  (ar:layer "ARKA_PANE_ZEWN_REF" 3)
  (ar:layer "ARKA_CENTRE" 6)
  (ar:layer "ARKA_INFO_NO_CUT" 8)
  (ar:poly "ARKA_OUTLINE" T (list (-3827.618886 1606.590478 0.0) (-3220.618886 1606.590478 0.0) (-3220.618886 2206.549644 0.417635)))
  (ar:poly "ARKA_PANE_ZEWN_REF" T (list (-3825.615541 1608.590478 0.0) (-3222.618886 1608.590478 0.0) (-3222.618886 2204.569575 0.415684)))
  (ar:poly "ARKA_OUTLINE" T (list (-3809.340469 1624.590478 0.0) (-3638.224536 1624.590478 -0.180632) (-3525.913841 1889.329085 0.0) (-3646.859695 2010.274939 0.185992)))
  (ar:poly "ARKA_PANE" T (list (-3811.399667 1622.590478 0.0) (-3636.305808 1622.590478 -0.18307) (-3523.119493 1889.363163 0.0) (-3646.884167 2013.127837 0.187809)))
  (ar:poly "ARKA_FRONT_HINGES_3MM" T (list (-3819.564829 1614.590478 0.0) (-3628.539077 1614.590478 -0.193085) (-3511.87493 1889.432309 0.0) (-3646.93261 2024.489989 0.194964)))
  (ar:poly "ARKA_OUTLINE" T (list (-3616.20221 1624.590478 0.0) (-3437.849711 1624.590478 -0.163389) (-3384.393705 1747.808948 0.0) (-3510.351602 1873.766845 0.179602)))
  (ar:poly "ARKA_PANE" T (list (-3618.291383 1622.590478 0.0) (-3436.005546 1622.590478 -0.167977) (-3381.631077 1747.874748 0.0) (-3510.388346 1876.632017 0.182343)))
  (ar:poly "ARKA_FRONT_HINGES_3MM" T (list (-3626.538677 1614.590478 0.0) (-3428.459619 1614.590478 -0.187298) (-3370.452697 1748.010076 0.0) (-3510.460712 1888.018091 0.193056)))
  (ar:poly "ARKA_OUTLINE" T (list (-3415.75979 1624.590478 0.0) (-3238.618886 1624.590478 0.0) (-3238.618886 1795.270101 0.369903)))
  (ar:poly "ARKA_PANE" T (list (-3417.947549 1622.590478 0.0) (-3236.618886 1622.590478 0.0) (-3236.618886 1797.378319 0.376343)))
  (ar:poly "ARKA_FRONT_HINGES_3MM" T (list (-3426.458017 1614.590478 0.0) (-3228.618886 1614.590478 0.0) (-3228.618886 1805.587966 0.401025)))
  (ar:poly "ARKA_OUTLINE" T (list (-3238.618886 2188.486517 0.189106) (-3631.303346 2025.831288 0.0) (-3510.357492 1904.885434 -0.185035) (-3238.618886 2017.44325 0.0)))
  (ar:poly "ARKA_PANE" T (list (-3236.618886 2190.521125 0.190914) (-3634.156245 2025.855759 0.0) (-3510.391571 1902.091085 -0.187498) (-3236.618886 2015.491444 0.0)))
  (ar:poly "ARKA_FRONT_HINGES_3MM" T (list (-3228.618886 2198.589634 0.198035) (-3645.518396 2025.904202 0.0) (-3510.460717 1890.846523 -0.197616) (-3228.618886 2007.589231 0.0)))
  (ar:poly "ARKA_OUTLINE" T (list (-3238.618886 1817.303553 0.0) (-3238.618886 1995.43492 0.184252) (-3494.795253 1889.323195 0.0) (-3368.837355 1763.365297 -0.171936)))
  (ar:poly "ARKA_PANE" T (list (-3236.618886 1815.396609 0.0) (-3236.618886 1997.486884 0.186974) (-3497.660424 1889.359939 0.0) (-3368.903155 1760.60267 -0.176615)))
  (ar:poly "ARKA_FRONT_HINGES_3MM" T (list (-3228.618886 1807.587991 0.0) (-3228.618886 2005.589225 0.19761) (-3509.046499 1889.432305 0.0) (-3369.038483 1749.424289 -0.196328)))
  (ar:poly "ARKA_MITRE" nil (list (-3819.172142 1629.584936 0.006335) (-3819.564829 1614.590478 0.0) (-3804.564829 1614.590478 0.0)))
  (ar:poly "ARKA_MITRE" nil (list (-3643.539077 1614.590478 0.0) (-3628.539077 1614.590478 -0.009352) (-3627.959435 1629.5784 0.0)))
  (ar:poly "ARKA_MITRE" nil (list (-3522.253733 1878.60391 -0.009352) (-3511.87493 1889.432309 0.0) (-3522.481532 1900.038911 0.0)))
  (ar:poly "ARKA_MITRE" nil (list (-3636.326008 2013.883387 0.0) (-3646.93261 2024.489989 0.006335) (-3657.385553 2013.732483 0.0)))
  (ar:poly "ARKA_MITRE" nil (list (-3625.956131 1629.578278 0.009399) (-3626.538677 1614.590478 0.0) (-3611.538677 1614.590478 0.0)))
  (ar:poly "ARKA_MITRE" nil (list (-3443.459619 1614.590478 0.0) (-3428.459619 1614.590478 -0.018659) (-3427.304159 1629.542418 0.0)))
  (ar:poly "ARKA_MITRE" nil (list (-3380.599056 1736.967115 -0.018659) (-3370.452697 1748.010076 0.0) (-3381.059298 1758.616677 0.0)))
  (ar:poly "ARKA_MITRE" nil (list (-3499.85411 1877.411489 0.0) (-3510.460712 1888.018091 0.009399) (-3520.838358 1877.188596 0.0)))
  (ar:poly "ARKA_MITRE" nil (list (-3425.29097 1629.541448 0.018846) (-3426.458017 1614.590478 0.0) (-3411.458017 1614.590478 0.0)))
  (ar:poly "ARKA_MITRE" nil (list (-3243.618886 1614.590478 0.0) (-3228.618886 1614.590478 0.0) (-3228.618886 1629.590478 0.0)))
  (ar:poly "ARKA_MITRE" nil (list (-3228.618886 1790.587966 0.0) (-3228.618886 1805.587966 0.018846) (-3243.601657 1804.947608 0.0)))
  (ar:poly "ARKA_MITRE" nil (list (-3228.618886 2183.589634 0.0) (-3228.618886 2198.589634 0.006335) (-3243.616938 2198.374275 0.0)))
  (ar:poly "ARKA_MITRE" nil (list (-3634.76089 2036.357146 0.006335) (-3645.518396 2025.904202 0.0) (-3634.911795 2015.297601 0.0)))
  (ar:poly "ARKA_MITRE" nil (list (-3521.067318 1901.453124 0.0) (-3510.460717 1890.846523 -0.009352) (-3499.632318 1901.225325 0.0)))
  (ar:poly "ARKA_MITRE" nil (list (-3243.614642 2007.271319 -0.009352) (-3228.618886 2007.589231 0.0) (-3228.618886 2022.589231 0.0)))
  (ar:poly "ARKA_MITRE" nil (list (-3243.601998 1806.953998 -0.018659) (-3228.618886 1807.587991 0.0) (-3228.618886 1822.587991 0.0)))
  (ar:poly "ARKA_MITRE" nil (list (-3228.618886 1990.589225 0.0) (-3228.618886 2005.589225 0.009399) (-3243.614599 2005.269719 0.0)))
  (ar:poly "ARKA_MITRE" nil (list (-3498.217003 1899.809951 0.009399) (-3509.046499 1889.432305 0.0) (-3498.439897 1878.825703 0.0)))
  (ar:poly "ARKA_MITRE" nil (list (-3379.645085 1760.030891 0.0) (-3369.038483 1749.424289 -0.018659) (-3357.995522 1759.570649 0.0)))
  (ar:point "ARKA_CENTRE" -3227.618886 1606.590478)
  (ar:poly "ARKA_SECTION" nil (list (-3120.618886 1606.590478 -0.414214) (-3112.618886 1614.590478 0.0) (-3112.618886 1620.590478 0.0)))
  (ar:text "ARKA_INFO_NO_CUT" -3124.618886 1587.590478 15.0 "START")
  (ar:text "ARKA_INFO_NO_CUT" -3100.618886 1610.590478 15.0 "SECTION R8 + 6 (VERBATIM)")
  (ar:text "ARKA_INFO_NO_CUT" -3120.618886 2184.590478 15.0 "DWG - TRACERY QUADRANT (LEFT HALF - MIRROR FOR THE RIGHT)")
  (ar:text "ARKA_INFO_NO_CUT" -3120.618886 2162.590478 15.0 "PATTERN QUAD-HUB-SPOKE SPOKES 5 RINGS 2 PANES 5")
  (ar:text "ARKA_INFO_NO_CUT" -3120.618886 2140.590478 15.0 "TIMBER BAR 22 EDGE MARGIN 18 PANE +2 LIMIT +10 MITRE LEG 15")
  (ar:text "ARKA_INFO_NO_CUT" -3120.618886 2118.590478 15.0 "ARKA_PANE = MOULDING RAIL (INNER EDGE OF THE BEAD), ARKA_FRONT_HINGES_3MM = BEAD LIMIT (NOT DRILLING)")
  (ar:text "ARKA_INFO_NO_CUT" -3120.618886 2096.590478 15.0 "NOT A TOOLPATH")
  (princ "\nARKA: tracery drawn. Layers ARKA_*; ARKA_INFO_NO_CUT is not a toolpath.")
  (princ)
)
(princ "\nARKA loaded - type ARKA to draw the tracery.")
(princ)
